package DE4SDV_ContextSpikeSnapshot {
  package Context {
    part def ConfigurableSDVProductLine;
    part def LifecycleEngineeringSystem;
    part def OpenInnovationEcosystem;
  }

  package EngineeringAssets {
    part def ModelRepository;
    part def ValidationPipeline;
    part def EvidenceBaseline;
  }
}
