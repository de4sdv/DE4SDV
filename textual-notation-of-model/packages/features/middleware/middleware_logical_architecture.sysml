/*
 * DE4SDV middleware logical architecture model slice in the SAF Conceptual Domain.
 *
 * INC-MW-007 allocates the technology-neutral middleware functions to logical
 * responsibilities and defines their internal exchanges. It does not select
 * ROS 2, DDS, AAOS SDV, S-CORE, AUTOSAR, processes, ECUs, networks, or a
 * physical deployment. The emergency intervention command path remains
 * outside this middleware logical architecture; only its health/protection
 * status is represented here.
 */

package DE4SDV_MiddlewareLogicalArchitecture {
  private import DE4SDV_MethodContext::*;
  private import DE4SDV_ProductLine::*;
  private import DE4SDV_MiddlewareOperationalContext::Features::Middleware::OperationalContext::*;
  private import DE4SDV_MiddlewareFunctionalArchitecture::Features::Middleware::FunctionalArchitecture::*;
  private import DE4SDV_MiddlewareRequirements::Features::Middleware::Requirements::*;
  private import DE4SDV_AEBSLogicalArchitecture::*;
  private import DE4SDV_Stakeholders::*;
  private import DE4SDV_TraceVocabulary::LogicalAllocationElement;
  private import SAF_Viewpoints::*;
  private import SysideViews::**;
  private import Views::*;

  part incMW007 : FeatureIncrement {
    doc /* INC-MW-007: middleware integration logical architecture. */
  }

  part systemSignalDefinitionGap : DeferredProductLineScope {
    doc /* GAP-MW-016: Conceptual signal contracts remain nominal until signal identity, units, freshness, and conversion rules are baselined. */
  }

  part systemServiceContractGap : DeferredProductLineScope {
    doc /* GAP-MW-017: System service discovery, authentication, and binding contracts remain technology-neutral and incomplete until physical interface selection. */
  }

  part systemSafetyOwnershipGap : DeferredProductLineScope {
    doc /* GAP-MW-018: Ownership and failure-response semantics for safety-path protection remain open pending safety analysis and physical realization. */
  }

  port def SignalAccessApplicationPort {
    in item signalRequest : VehicleSignalAccessRequest;
    out item signalResponse : VehicleSignalAccessResponse;
  }

  port def DiagnosticApplicationPort {
    in item diagnosticRequest : DiagnosticAccessRequest;
    out item diagnosticResponse : DiagnosticAccessResponse;
  }

  port def LifecycleApplicationPort {
    in item lifecycleRequest : LifecycleCoordinationRequest;
    out item lifecycleStatus : LifecycleCoordinationStatus;
  }

  port def HealthApplicationPort {
    out item forwardedHealth : HealthForwardingStatus;
  }

  port def UpdateApplicationPort {
    in item updateNotification : UpdateNotification;
    out item updateStatus : UpdateCoordinationStatus;
  }

  port def ServiceBindingApplicationPort {
    in item bindingRequest : ServiceBindingRequest;
    out item bindingStatus : ServiceBindingStatus;
  }

  port def SafetyPathObservationPort {
    out item safetyPathStatus : SafetyPathProtectionStatus;
  }

  part def SignalTranslator :> LogicalAllocationElement {
    doc /* Conceptual responsibility for translating and exposing vehicle-signal access without selecting a signal schema or transport. */
    port application : SignalAccessApplicationPort;
  }

  part def DiagnosticProxy :> LogicalAllocationElement {
    doc /* Conceptual responsibility for proxying diagnostic requests and responses across the middleware boundary. */
    port application : DiagnosticApplicationPort;
  }

  part def LifecycleBridge :> LogicalAllocationElement {
    doc /* Conceptual responsibility for coordinating application-visible lifecycle state with middleware lifecycle state. */
    port application : LifecycleApplicationPort;
  }

  part def HealthProxy :> LogicalAllocationElement {
    doc /* Conceptual responsibility for forwarding service health and availability status. */
    port application : HealthApplicationPort;
    port safetyObservation : SafetyPathObservationPort;
    exhibit state healthStates {
      state unavailable;
      state degraded;
      state available;
    }
  }

  part def UpdateCoordinator :> LogicalAllocationElement {
    doc /* Conceptual responsibility for coordinating integration updates without selecting an update mechanism. */
    port application : UpdateApplicationPort;
  }

  part def ServiceBindingManager :> LogicalAllocationElement {
    doc /* Conceptual responsibility for service discovery, authentication boundary handling, and service binding. */
    port application : ServiceBindingApplicationPort;
  }

  part def MiddlewareSystem {
    doc /* Technology-neutral logical composition of the middleware integration responsibilities. */
    port signalAccess : SignalAccessApplicationPort;
    port diagnosticAccess : DiagnosticApplicationPort;
    port lifecycle : LifecycleApplicationPort;
    port health : HealthApplicationPort;
    port update : UpdateApplicationPort;
    port serviceBinding : ServiceBindingApplicationPort;
    port safetyPathObservation : SafetyPathObservationPort;

    part signalTranslator : SignalTranslator;
    part diagnosticProxy : DiagnosticProxy;
    part lifecycleBridge : LifecycleBridge;
    part healthProxy : HealthProxy;
    part updateCoordinator : UpdateCoordinator;
    part serviceBindingManager : ServiceBindingManager;

    exhibit state lifecycleStates {
      state uninitialized;
      state initializing;
      state operational;
      state degraded;
      state shuttingDown;
    }

    bind signalAccess = signalTranslator.application;
    bind diagnosticAccess = diagnosticProxy.application;
    bind lifecycle = lifecycleBridge.application;
    bind health = healthProxy.application;
    bind update = updateCoordinator.application;
    bind serviceBinding = serviceBindingManager.application;
    bind safetyPathObservation = healthProxy.safetyObservation;
  }

  action functionalFlow : MiddlewareIntegrationFunctionalFlow;
  part system : MiddlewareSystem;

  allocation def FunctionalToSystemResponsibility;

  allocation signalTranslationAllocation : FunctionalToSystemResponsibility
    allocate functionalFlow::translateSignal
    to system.signalTranslator;
  allocation diagnosticProxyAllocation : FunctionalToSystemResponsibility
    allocate functionalFlow::proxyDiagnostics
    to system.diagnosticProxy;
  allocation lifecycleBridgeAllocation : FunctionalToSystemResponsibility
    allocate functionalFlow::coordinateLifecycle
    to system.lifecycleBridge;
  allocation healthProxyAllocation : FunctionalToSystemResponsibility
    allocate functionalFlow::forwardHealth
    to system.healthProxy;
  allocation updateCoordinatorAllocation : FunctionalToSystemResponsibility
    allocate functionalFlow::coordinateUpdate
    to system.updateCoordinator;
  allocation serviceBindingAllocation : FunctionalToSystemResponsibility
    allocate functionalFlow::bindService
    to system.serviceBindingManager;
  allocation safetyPathObservationAllocation : FunctionalToSystemResponsibility
    allocate functionalFlow::protectSafetyPath
    to system.healthProxy;

  dependency signalTranslatorDerivedFromRequirement
    from system::signalTranslator
    to DE4SDV_MiddlewareRequirements::Features::Middleware::Requirements::reqProvideMiddlewareSignalAccess;
  dependency diagnosticProxyDerivedFromRequirement
    from system::diagnosticProxy
    to DE4SDV_MiddlewareRequirements::Features::Middleware::Requirements::reqProvideMiddlewareDiagnosticAccess;
  dependency lifecycleBridgeDerivedFromRequirement
    from system::lifecycleBridge
    to DE4SDV_MiddlewareRequirements::Features::Middleware::Requirements::reqCoordinateMiddlewareLifecycle;
  dependency healthProxyDerivedFromRequirement
    from system::healthProxy
    to DE4SDV_MiddlewareRequirements::Features::Middleware::Requirements::reqMonitorMiddlewareHealth;
  dependency updateCoordinatorDerivedFromRequirement
    from system::updateCoordinator
    to DE4SDV_MiddlewareRequirements::Features::Middleware::Requirements::reqCoordinateMiddlewareUpdates;
  dependency serviceBindingDerivedFromRequirement
    from system::serviceBindingManager
    to DE4SDV_MiddlewareRequirements::Features::Middleware::Requirements::reqProvideServiceDiscovery;

  dependency aebsVehicleMotionDependsOnSignalTranslator
    from DE4SDV_AEBSLogicalArchitecture::system::vehicleMotionObservationIn
    to system::signalTranslator;
  dependency aebsTargetObservationDependsOnSignalTranslator
    from DE4SDV_AEBSLogicalArchitecture::system::targetObservationIn
    to system::signalTranslator;
  dependency aebsDriverOverrideDependsOnSignalTranslator
    from DE4SDV_AEBSLogicalArchitecture::system::driverOverrideObservationIn
    to system::signalTranslator;
  dependency aebsOperatingContextDependsOnLifecycleBridge
    from DE4SDV_AEBSLogicalArchitecture::system::operatingContextIn
    to system::lifecycleBridge;
  dependency aebsHealthStatusDependsOnHealthProxy
    from DE4SDV_AEBSLogicalArchitecture::system::subsystemHealthIn
    to system::healthProxy;

  dependency systemFunctionalArchitectureBaselineTrace
    from system
    to DE4SDV_MiddlewareFunctionalArchitecture::Features::Middleware::FunctionalArchitecture::middlewareFunctionalBoundary;

  concern conceptualStructureConcern : ConceptualStructureConcern {
    subject;
    stakeholder systemsEngineer : SystemsEngineer;
    stakeholder reviewer : OpenSourceReviewer;
  }

  concern conceptualInternalExchangeConcern : ConceptualInternalExchangeConcern {
    doc /*
     * Known issue: no view is published for this concern yet. The current
     * conceptual architecture models boundary delegations from MiddlewareSystem
     * ports to owned responsibility ports, but no cross-component connections or
     * item flows. Native rendering of those bindings produces assignment/end
     * notation rather than a reviewable internal-exchange diagram. The boundary
     * delegations remain in the model; publish this view only after authoritative
     * cross-component interfaces, connections, and exchanged items are modeled.
     */
    subject;
    stakeholder systemsEngineer : SystemsEngineer;
    stakeholder reviewer : OpenSourceReviewer;
  }

  concern conceptualFunctionMappingConcern : ConceptualFunctionMappingConcern {
    subject;
    stakeholder systemsEngineer : SystemsEngineer;
    stakeholder reviewer : OpenSourceReviewer;
  }

  view middlewareSystemStructureView {
    viewpoint selectedSystemStructureViewpoint : SystemStructureDefinitionViewpoint {
      frame conceptualStructureConcern;
    }
    expose MiddlewareSystem;
    attribute depth = 1;
    attribute showAnnotationRows = false;
    attribute maxCompartmentEntries = 6;
    render asTreeDiagram;
  }

  view middlewareSystemFunctionMappingView : MVD::MatrixView {
    viewpoint selectedSystemFunctionMappingViewpoint : SystemFunctionMappingViewpoint {
      frame conceptualFunctionMappingConcern;
    }
    view :>> rowView {
      expose functionalFlow::translateSignal;
      expose functionalFlow::proxyDiagnostics;
      expose functionalFlow::coordinateLifecycle;
      expose functionalFlow::forwardHealth;
      expose functionalFlow::coordinateUpdate;
      expose functionalFlow::bindService;
      expose functionalFlow::protectSafetyPath;
      attribute :>> representation = Rep::name;
    }
    view :>> columnView {
      expose system::signalTranslator;
      expose system::diagnosticProxy;
      expose system::lifecycleBridge;
      expose system::healthProxy;
      expose system::updateCoordinator;
      expose system::serviceBindingManager;
      attribute :>> representation = Rep::name;
    }
    view :>> cellView {
      expose DE4SDV_MiddlewareLogicalArchitecture::*;
      attribute :>> direction = SysideViews::MatrixTraceabilityDirection::row2col;
    }
  }
}
