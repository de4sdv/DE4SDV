/*
 * DE4SDV middleware design-input requirement model slice.
 *
 * INC-MW-005 derives draft, verifiable requirement candidates from the
 * stakeholder needs in INC-MW-004. This slice does not define functional,
 * logical, or physical architecture; those follow in INC-MW-006 through
 * INC-MW-008.
 */

package DE4SDV_MiddlewareRequirements {
  package Features {
    package Middleware {
      package Requirements {
        private import Views::*;
        private import StandardViewDefinitions::*;
        private import DE4SDV_Stakeholders::*;
        private import DE4SDV_MethodContext::*;
        private import DE4SDV_ProductLine::*;
        private import DE4SDV_MethodViewpoints::*;
        private import SAF_Viewpoints::*;
        private import SysideViews::**;
        private import DE4SDV_MiddlewareOperationalContext::Features::Middleware::OperationalContext::*;
        private import DE4SDV_MiddlewareFunctionalArchitecture::Features::Middleware::FunctionalArchitecture::*;
        private import DE4SDV_MiddlewareStakeholderNeeds::Features::Middleware::StakeholderNeeds::System1Product::*;
        private import DE4SDV_MiddlewareIncrementFraming::Features::Middleware::IncrementFraming::*;

        requirement def MiddlewareSignalAccessRequirement :> FunctionalRequirementCandidate;
        requirement def MiddlewareDiagnosticAccessRequirement :> FunctionalRequirementCandidate;
        requirement def MiddlewareLifecycleCoordinationRequirement :> FunctionalRequirementCandidate;
        requirement def MiddlewareHealthMonitoringRequirement :> FunctionalRequirementCandidate;
        requirement def MiddlewareUpdateCoordinationRequirement :> FunctionalRequirementCandidate;
        requirement def MiddlewareSafetyPathIsolationRequirement :> SafetyConstraintRequirementCandidate;
        requirement def MiddlewareServiceDiscoveryRequirement :> FunctionalRequirementCandidate;
        requirement def MiddlewareBoundaryTraceabilityRequirement :> TraceabilityConstraintRequirementCandidate;
        requirement def MiddlewareServiceAuthenticationRequirement :> SecurityConstraintRequirementCandidate;

        part incMW005 : NeedsRequirementsIncrement {
          doc /* INC-MW-005: middleware integration design-input requirements. */
        }

        package System1Product {
          requirement reqProvideMiddlewareSignalAccess : MiddlewareSignalAccessRequirement {
            doc /* REQ-MW-001 draft design-input requirement. */
            subject memberProduct : ProductLineMemberProduct;
            require constraint statement { language "English" /* Each SDV product-line member product shall provide the ADAS application access to the vehicle signals required by its selected operational use cases through the selected middleware integration boundary. */ }
            attribute :>> status = ReqStatus::ReadyForReview;
            attribute :>> source = "Derived from N-MW-001";
            attribute :>> rationale = "Signal access is the core middleware integration service for the ADAS application.";
          }

          requirement reqProvideMiddlewareDiagnosticAccess : MiddlewareDiagnosticAccessRequirement {
            doc /* REQ-MW-002 draft design-input requirement. */
            subject memberProduct : ProductLineMemberProduct;
            require constraint statement { language "English" /* Each SDV product-line member product shall provide the ADAS application access to middleware and vehicle diagnostic status from which the health of the selected integration boundary can be determined. */ }
            attribute :>> status = ReqStatus::ReadyForReview;
            attribute :>> source = "Derived from N-MW-001";
            attribute :>> rationale = "Boundary health determinations require diagnostic visibility.";
          }

          requirement reqCoordinateMiddlewareLifecycle : MiddlewareLifecycleCoordinationRequirement {
            doc /* REQ-MW-003 draft design-input requirement. */
            subject memberProduct : ProductLineMemberProduct;
            require constraint statement { language "English" /* Each SDV product-line member product shall coordinate middleware integration lifecycle state with the ADAS application so that startup, readiness, degraded operation, and shutdown transitions are observable at the integration boundary. */ }
            attribute :>> status = ReqStatus::ReadyForReview;
            attribute :>> source = "Derived from N-MW-001";
            attribute :>> rationale = "Lifecycle transitions must be observable at the integration boundary.";
          }

          requirement reqMonitorMiddlewareHealth : MiddlewareHealthMonitoringRequirement {
            doc /* REQ-MW-004 draft design-input requirement. */
            subject memberProduct : ProductLineMemberProduct;
            require constraint statement { language "English" /* Each SDV product-line member product shall monitor the health of the selected middleware integration boundary and provide an observable indication when a required integration service is stale, missing, inconsistent, or unavailable. */ }
            attribute :>> status = ReqStatus::ReadyForReview;
            attribute :>> source = "Derived from N-MW-001";
            attribute :>> rationale = "Degraded integration services must be detected and indicated.";
          }

          requirement reqCoordinateMiddlewareUpdates : MiddlewareUpdateCoordinationRequirement {
            doc /* REQ-MW-005 draft design-input requirement. */
            subject memberProduct : ProductLineMemberProduct;
            require constraint statement { language "English" /* Each SDV product-line member product shall coordinate middleware integration updates with the ADAS application lifecycle so that an update does not silently invalidate required signal, diagnostic, lifecycle, or health interfaces. */ }
            attribute :>> status = ReqStatus::ReadyForReview;
            attribute :>> source = "Derived from N-MW-001";
            attribute :>> rationale = "Updates must not silently invalidate required interfaces.";
          }

          requirement reqIsolateSafetyPath : MiddlewareSafetyPathIsolationRequirement {
            doc /* REQ-MW-006 draft safety-constraint requirement; architecture choice and containment criteria remain open per GAP-MW-029. */
            subject memberProduct : ProductLineMemberProduct;
            require constraint statement { language "English" /* Each SDV product-line member product shall prevent a failure of the non-safety middleware integration path from causing an uncontrolled emergency intervention command, whether the selected realization uses a safety-certified middleware partition or a direct vehicle-command path. */ }
            attribute :>> status = ReqStatus::InDevelopment;
            attribute :>> source = "Derived from N-MW-004";
            attribute :>> rationale = "Middleware failure must not cause uncontrolled emergency intervention; containment criteria open per GAP-MW-029.";
          }

          requirement reqProvideServiceDiscovery : MiddlewareServiceDiscoveryRequirement {
            doc /* REQ-MW-007 draft design-input requirement. */
            subject memberProduct : ProductLineMemberProduct;
            require constraint statement { language "English" /* Each SDV product-line member product shall discover and bind the middleware services required by the selected ADAS application integration configuration before those services are used. */ }
            attribute :>> status = ReqStatus::ReadyForReview;
            attribute :>> source = "Derived from N-MW-002";
            attribute :>> rationale = "Services must be bound before use for decoupled integration.";
          }

          requirement reqAuthenticateServiceBinding : MiddlewareServiceAuthenticationRequirement {
            doc /* REQ-MW-008 draft security constraint derived from N-MW-009; trust-boundary details remain deferred per GAP-MW-012. */
            subject memberProduct : ProductLineMemberProduct;
            require constraint statement { language "English" /* Each SDV product-line member product shall authenticate a middleware service binding before accepting service data or commands across a trust boundary defined for the selected integration configuration. */ }
            attribute :>> status = ReqStatus::InDevelopment;
            attribute :>> source = "Derived from N-MW-009";
            attribute :>> rationale = "Service data and commands across a trust boundary must be authenticated; boundary details deferred per GAP-MW-012.";
          }
        }

        package System2EngineeringAssurance {
          requirement reqMaintainMiddlewareBoundaryTraceability : MiddlewareBoundaryTraceabilityRequirement {
            doc /* REQ-MW-009 System 2 traceability requirement. */
            subject increment : NeedsRequirementsIncrement;
            require constraint statement { language "English" /* The DE4SDV middleware increment shall maintain trace links from each middleware requirement to its stakeholder need, operational-context source, feature/common-capability classification, unresolved gap, and planned verification record. */ }
            attribute :>> status = ReqStatus::ReadyForReview;
            attribute :>> source = "Derived from N-MW-006";
            attribute :>> rationale = "Trace links are the increment's assurance backbone.";
          }
        }

        dependency reqProvideMiddlewareSignalAccessDerivedFromMiddlewareIntegration
          from reqProvideMiddlewareSignalAccess
          to DE4SDV_MiddlewareStakeholderNeeds::Features::Middleware::StakeholderNeeds::needMiddlewareIntegration;
        dependency reqProvideMiddlewareDiagnosticAccessDerivedFromMiddlewareIntegration
          from reqProvideMiddlewareDiagnosticAccess
          to DE4SDV_MiddlewareStakeholderNeeds::Features::Middleware::StakeholderNeeds::needMiddlewareIntegration;
        dependency reqCoordinateMiddlewareLifecycleDerivedFromMiddlewareIntegration
          from reqCoordinateMiddlewareLifecycle
          to DE4SDV_MiddlewareStakeholderNeeds::Features::Middleware::StakeholderNeeds::needMiddlewareIntegration;
        dependency reqMonitorMiddlewareHealthDerivedFromMiddlewareIntegration
          from reqMonitorMiddlewareHealth
          to DE4SDV_MiddlewareStakeholderNeeds::Features::Middleware::StakeholderNeeds::needMiddlewareIntegration;
        dependency reqCoordinateMiddlewareUpdatesDerivedFromMiddlewareIntegration
          from reqCoordinateMiddlewareUpdates
          to DE4SDV_MiddlewareStakeholderNeeds::Features::Middleware::StakeholderNeeds::needMiddlewareIntegration;
        dependency reqIsolateSafetyPathDerivedFromSafetyPathIsolation
          from reqIsolateSafetyPath
          to DE4SDV_MiddlewareStakeholderNeeds::Features::Middleware::StakeholderNeeds::needSafetyPathIsolation;
        dependency reqProvideServiceDiscoveryDerivedFromPlatformDecoupling
          from reqProvideServiceDiscovery
          to DE4SDV_MiddlewareStakeholderNeeds::Features::Middleware::StakeholderNeeds::needPlatformDecoupling;
        dependency reqAuthenticateServiceBindingDerivedFromSecurityTrustBoundary
          from reqAuthenticateServiceBinding
          to DE4SDV_MiddlewareStakeholderNeeds::Features::Middleware::StakeholderNeeds::System2EngineeringAssurance::needSecurityTrustBoundary;
        dependency reqMaintainMiddlewareBoundaryTraceabilityDerivedFromTraceabilityToOperationalContext
          from reqMaintainMiddlewareBoundaryTraceability
          to DE4SDV_MiddlewareStakeholderNeeds::Features::Middleware::StakeholderNeeds::needTraceabilityToOperationalContext;

        /* Requirement traceability to the operational use cases that justify
         * each requirement (SystemRequirementTraceabilityViewpoint targets:
         * use case, process, context). Each requirement is justified by the
         * operational scenario it enables. */
        dependency reqProvideMiddlewareSignalAccessTracedToExchangeVehicleSignals
          from reqProvideMiddlewareSignalAccess
          to 'exchange vehicle signals';
        dependency reqProvideMiddlewareSignalAccessTracedToTranslateSignalAction
          from reqProvideMiddlewareSignalAccess
          to middlewareIntegrationFunctionalFlow::translateSignal;
        dependency reqProvideMiddlewareDiagnosticAccessTracedToAccessDiagnostics
          from reqProvideMiddlewareDiagnosticAccess
          to 'access diagnostics';
        dependency reqProvideMiddlewareDiagnosticAccessTracedToProxyDiagnosticsAction
          from reqProvideMiddlewareDiagnosticAccess
          to middlewareIntegrationFunctionalFlow::proxyDiagnostics;
        dependency reqCoordinateMiddlewareLifecycleTracedToCoordinateLifecycle
          from reqCoordinateMiddlewareLifecycle
          to 'coordinate lifecycle';
        dependency reqCoordinateMiddlewareLifecycleTracedToCoordinateLifecycleAction
          from reqCoordinateMiddlewareLifecycle
          to middlewareIntegrationFunctionalFlow::coordinateLifecycle;
        dependency reqMonitorMiddlewareHealthTracedToMonitorServiceHealth
          from reqMonitorMiddlewareHealth
          to 'monitor service health';
        dependency reqMonitorMiddlewareHealthTracedToForwardHealthAction
          from reqMonitorMiddlewareHealth
          to middlewareIntegrationFunctionalFlow::forwardHealth;
        dependency reqCoordinateMiddlewareUpdatesTracedToCoordinateUpdate
          from reqCoordinateMiddlewareUpdates
          to 'coordinate software update';
        dependency reqCoordinateMiddlewareUpdatesTracedToCoordinateUpdateAction
          from reqCoordinateMiddlewareUpdates
          to middlewareIntegrationFunctionalFlow::coordinateUpdate;
        dependency reqIsolateSafetyPathTracedToEmergencySafetyPath
          from reqIsolateSafetyPath
          to 'emergency intervention via safety path';
        dependency reqIsolateSafetyPathTracedToProtectSafetyPathAction
          from reqIsolateSafetyPath
          to middlewareIntegrationFunctionalFlow::protectSafetyPath;
        dependency reqProvideServiceDiscoveryTracedToExchangeVehicleSignals
          from reqProvideServiceDiscovery
          to 'exchange vehicle signals';
        dependency reqProvideServiceDiscoveryTracedToBindServiceAction
          from reqProvideServiceDiscovery
          to middlewareIntegrationFunctionalFlow::bindService;
        dependency reqAuthenticateServiceBindingTracedToExchangeVehicleSignals
          from reqAuthenticateServiceBinding
          to 'exchange vehicle signals';
        dependency reqAuthenticateServiceBindingTracedToBindServiceAction
          from reqAuthenticateServiceBinding
          to middlewareIntegrationFunctionalFlow::bindService;

        public import System1Product::*;
        public import System2EngineeringAssurance::*;

        dependency requirementNeedsTrace
          from DE4SDV_MiddlewareRequirements::Features::Middleware::Requirements::System1Product::reqProvideMiddlewareSignalAccess
          to DE4SDV_MiddlewareStakeholderNeeds::Features::Middleware::StakeholderNeeds::System1Product::needMiddlewareIntegration;
        dependency requirementOperationalContextTrace
          from DE4SDV_MiddlewareRequirements::Features::Middleware::Requirements::System1Product::reqProvideMiddlewareSignalAccess
          to DE4SDV_MiddlewareOperationalContext::Features::Middleware::OperationalContext::'integrate ADAS with vehicle platform';
        dependency requirementFramingTrace
          from DE4SDV_MiddlewareRequirements::Features::Middleware::Requirements::System1Product::reqProvideMiddlewareSignalAccess
          to DE4SDV_MiddlewareIncrementFraming::Features::Middleware::IncrementFraming::middlewareIntegrationProblemStatement;

        concern requirementTraceConcern : RequirementTraceConcern {
          subject;
          stakeholder systemsEngineer : SystemsEngineer;
          stakeholder verificationEngineer : VerificationEngineer;
          stakeholder reviewer : OpenSourceReviewer;
        }

        view middlewareSystemRequirementsView : TVD::TableView {
          viewpoint selectedSystemRequirementsViewpoint : SystemRequirementDefinitionViewpoint {
            frame requirementTraceConcern;
          }
          expose System1Product::*;
          expose System2EngineeringAssurance::*;
          filter @ SysML::RequirementUsage;
          attribute :>> includeReferenceElements = true;
          attribute :>> maxRowHeight = 300;
          view ID :> columnViews {
            attribute :>> featureToRender = CT::declaredName;
          }
          view Name :> columnViews {
            attribute :>> featureToRender = CT::heritage;
          }
          view Statement :> columnViews {
            attribute :>> featureToRender = CT::constraintLanguage {
              attribute constraintName = "statement";
              attribute constraintType = CL::ConT::required;
              attribute constraintLanguage = "English";
            }
            attribute :>> columnWidth = 360;
          }
        }
        view middlewareRequirementTraceView : GeneralView {
          viewpoint selectedRequirementTraceViewpoint : SystemRequirementTraceabilityViewpoint {
            frame requirementTraceConcern;
          }
          expose System1Product::*;
          expose System2EngineeringAssurance::*;
          expose DE4SDV_MiddlewareOperationalContext::Features::Middleware::OperationalContext::'exchange vehicle signals';
          expose DE4SDV_MiddlewareOperationalContext::Features::Middleware::OperationalContext::'access diagnostics';
          expose DE4SDV_MiddlewareOperationalContext::Features::Middleware::OperationalContext::'coordinate lifecycle';
          expose DE4SDV_MiddlewareOperationalContext::Features::Middleware::OperationalContext::'monitor service health';
          expose DE4SDV_MiddlewareOperationalContext::Features::Middleware::OperationalContext::'coordinate software update';
          expose DE4SDV_MiddlewareOperationalContext::Features::Middleware::OperationalContext::'emergency intervention via safety path';
          expose DE4SDV_MiddlewareFunctionalArchitecture::Features::Middleware::FunctionalArchitecture::middlewareIntegrationFunctionalFlow;
          attribute depth = 1;
        }
      }
    }
  }
}
