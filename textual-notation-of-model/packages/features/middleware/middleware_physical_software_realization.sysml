/*
 * DE4SDV middleware physical/software realization model slice.
 *
 * INC-MW-008 maps the middleware logical responsibilities to a concrete
 * candidate software/platform boundary: the Autoware-to-AAOS SDV adapter and
 * the AAOS SDV boundary model. This is a model of the integration boundary,
 * not a vendored AAOS implementation. A bounded Vehicle.Speed
 * AAOS/Cuttlefish-to-ROS 2 campaign path is represented separately below as
 * System 2 evidence transport; it is not production middleware runtime
 * deployment or native SDV transport interoperability evidence.
 *
 * The adapter and AAOS boundary remain candidate realizations. The selected
 * Autoware ROS 2 topic and AOSP SDV gateway/middleware source artifacts are
 * pinned. The vehicle-velocity VSIDL service bundle remains a DE4SDV reference
 * contract, while production process deployment and executable behavior remain
 * deferred until their target-owned source contracts are pinned.
 */

package DE4SDV_MiddlewarePhysicalSoftwareRealization {
  private import DE4SDV_MethodContext::*;
  private import DE4SDV_MethodProcess::*;
  private import DE4SDV_ProductLine::*;
  private import DE4SDV_Stakeholders::*;
  private import DE4SDV_ExecutionEnvironments::*;
  private import DE4SDV_MiddlewareLogicalArchitecture::*;
  private import DE4SDV_SDVPlatformStack::*;
  private import DE4SDV_AAOSSDVMiddlewareBoundary::*;
  private import DE4SDV_AEBSPhysicalSoftwareRealization::*;
  private import DE4SDV_ROS2Types::*;
  private import DE4SDV_TraceVocabulary::PhysicalAllocationElement;
  private import COVESA_VSS::**;
  private import SAF_Viewpoints::*;
  private import SysideViews::**;
  private import Views::*;

  part incMW008 : FeatureIncrement {
    doc /* INC-MW-008: middleware integration physical/software realization. */
  }

  part physicalSourceContractGap : DeferredProductLineScope {
    doc /*
     * GAP-MW-019: The Autoware ROS 2 topic and AOSP SDV transport sources are
     * pinned, and the selected vehicle-velocity VSIDL/service-bundle schema
     * (de4sdv.reference.vehicle_speed) with its generated client binding is
     * now exercised at runtime (E-MW-012). The generated binding remains a
     * staging artifact (stage_aosp_bridge.sh), not a committed production
     * contract; the production adapter-chain binding decision remains open.
     */
  }

  part physicalProcessDeploymentGap : DeferredProductLineScope {
    doc /*
     * GAP-MW-020: No System 1 production adapter process, executor, runtime,
     * VM, or network deployment is selected. The bounded Vehicle.Speed
     * campaign deployment below is System 2 evidence infrastructure and must
     * not be read as the production deployment decision.
     */
  }

  part physicalServiceSatisfactionGap : DeferredProductLineScope {
    doc /* GAP-MW-021: The candidate AAOS SDV boundary has not been shown to satisfy the logical service responsibilities or requirements. */
  }

  part physicalEnablingSystemGap : DeferredProductLineScope {
    doc /*
     * GAP-MW-023: The bounded campaign exercised one AAOS/Cuttlefish host and
     * one ROS 2 host, but no reusable or selected System 2 capability envelope
     * is baselined for future campaigns. The observed campaign hosts do not
     * establish a System 1 product deployment.
     */
  }

  part velocitySignalContractGap : DeferredProductLineScope {
    doc /*
     * GAP-MW-022: The pinned public AOSP SDV tree provides gateway,
     * service-discovery, data-tunnel, RPC-agent, and transport interfaces,
     * but the selected production vehicle-velocity VSIDL service bundle,
     * FQIN, payload contract, or generated client binding were not
     * established. The DE4SDV reference payload and VSIDL catalog remain
     * candidate-only. The campaign path now exercises the reference
     * provider/observer bundles end-to-end (E-MW-012) through the dedicated
     * observer domain; the production deployment decision remains open.
     */
  }

  part def AAOSSDVSourceArtifact {
    doc /*
     * Source ID: AOSP-AAOS-SDV-MANIFEST.
     * Pinned AOSP source manifest and build target for the AAOS SDV build.
     * Detailed repository, revision, branch, and path provenance is maintained
     * in the INC-MW-008 pilot source_alignment record.
     */
  }

  part def COVESAVehicleSpeedSemanticSource {
    doc /*
     * Source ID: COVESA-VSS-VEHICLE-SPEED.
     * Source-backed semantic definition for VSS Vehicle.Speed. This is the
     * canonical vehicle-speed meaning used between the AAOS contract and the
     * Autoware ROS 2 representation; it is not an AAOS VSIDL service contract.
     * VSS path: Vehicle.Speed; quantity: speed; unit: km/h.
     * The canonical field/unit transformation is recorded by mapping
     * VSS-SIM-AEBS-001 in
     * methodologies/sysmod-sysmlv2/pilots/aebs-simulation-deployment/
     * vss-simulation-realization.yaml; this increment traces that mapping
     * rather than redefining it.
     */
  }

  part def DE4SDVVSSVehicleSpeedAdapterSource {
    doc /*
     * Source ID: DE4SDV-VSS-VEHICLE-SPEED-ADAPTER.
     * Source-backed DE4SDV provider-neutral adapter implementation.
     * This implementation normalizes VSS Vehicle.Speed [km/h] to a
     * provider-neutral longitudinal velocity [m/s]. It does not claim AAOS,
     * VSIDL, ROS 2, transport, deployment, or runtime interoperability.
     */
  }

  part def DE4SDVAAOSSDVReferenceInteropBenchSource {
    doc /*
     * Source ID: DE4SDV-AAOS-SDV-REFERENCE-INTEROP-BENCH.
     * Source-backed DE4SDV-owned reference contract and executable rehearsal.
     * The reference protobuf message is `VehicleSpeed` with the semantic
     * field `speed_kmh`; the companion VSIDL catalog identifies the
     * `VehicleSpeedProvider` publisher, `VehicleSpeed` message, and
     * `VEHICLE_SPEED` channel. These artifacts define a reference contract
     * candidate, not a selected OEM or production AAOS service.
     * The bounded campaign proves the reference provider/observer path,
     * structured logcat extraction, host-side forwarding, private TCP transfer,
     * ROS 2 publication, and independent observation for one target execution.
     * It remains a development-campaign transport slice, not an OEM contract,
     * production deployment, or native SDV transport result.
     */
  }

  item def DE4SDVReferenceVehicleSpeedPayload {
    doc /*
     * Candidate semantic payload slice for the DE4SDV-owned reference
     * contract. `speed_kmh` is the explicit identity mapping from COVESA VSS
     * `Vehicle.Speed` [km/h]. The reference protobuf also carries timestamp
     * and quality fields; their semantics remain outside this signal slice
     * until they are separately mapped.
     */
    attribute speed_kmh : Vehicle_Speed;
  }

  port def DE4SDVReferenceVehicleSpeedAccessPort :> VehicleSignalAccessPort {
    doc /*
     * Candidate typed AAOS-side access port for the reference vehicle-speed
     * slice. The type binds the current signal boundary to the reference
     * payload without selecting a production VSIDL service, generated
     * binding, deployment, or runtime transport.
     */
    inout item vehicleSpeed : DE4SDVReferenceVehicleSpeedPayload redefines vehicleSignals;
  }

  part def AAOSVSIDLProviderAgentSource {
    doc /*
     * Source ID: AOSP-AAOS-SDV-VSIDL.
     * VSIDL provider agent from
     * system/software_defined_vehicle/vsidl/provider/agent/sdv. The pinned
     * implementation exposes metadata RPCs including diagnostics declaration,
     * message descriptor, publication descriptor, and RPC method descriptor.
     */
  }

  part def AAOSMiddlewareSource {
    doc /*
     * Source ID: AOSP-AAOS-SDV-MIDDLEWARE.
     * Source-backed AAOS SDV middleware communication implementation from
     * system/software_defined_vehicle/middleware.
     * The pinned source provides the middleware communication boundary.
     */
  }

  part def AAOSHardwareSDVInterfacesSource {
    doc /*
     * Source ID: AOSP-AAOS-SDV-INTERFACES.
     * Source-backed hardware/sdv interface definitions for middleware,
     * lifecycle, service discovery, RPC, and data-tunnel boundaries.
     */
  }

  part def AAOSSDVGatewaySessionSource {
    doc /*
     * Source ID: AOSP-AAOS-SDV-INTERFACES.
     * Source-backed AAOS SDV gateway session interface. It exposes
     * serviceDiscoveryAgent(), dataTunnelAgent(), createPublication(), and
     * findRpcServerByName().
     */
  }

  part def AAOSSDVDataTunnelPublicationSource {
    doc /*
     * Source ID: AOSP-AAOS-SDV-INTERFACES.
     * Source-backed AAOS SDV data-tunnel publication interface. It exposes
     * publication ownership and publisher metadata at the gateway boundary.
     */
  }

  part def AAOSSDVRpcAgentSource {
    doc /*
     * Source ID: AOSP-AAOS-SDV-MIDDLEWARE.
     * Source-backed AAOS SDV RPC-agent implementation. It registers RPC
     * servers and transport metadata with the SDV middleware.
     */
  }

  part def AAOSLifecycleServiceSource {
    doc /*
     * Source ID: AOSP-AAOS-SDV-LIFECYCLE.
     * Source-backed lifecycle-management project at
     * system/software_defined_vehicle/lifecycle_management.
     */
  }

  part def AAOSHealthMonitorSource {
    doc /*
     * Source ID: AOSP-AAOS-SDV-HEALTH.
     * Source-backed health-monitor project at
     * system/software_defined_vehicle/health_monitor.
     */
  }

  part def AAOSDiagnosticsSource {
    doc /*
     * Source ID: AOSP-AAOS-SDV-DIAGNOSTICS.
     * Source-backed automotive diagnostics project at
     * system/software_defined_vehicle/automotive_services, relevant source
     * area: diagnostics.
     */
  }

  part def SignalAccessClient :> PhysicalAllocationElement {
    doc /* Candidate generic physical/software client for vehicle signal access through the selected adapter and platform boundary. Concrete signal slices specialize the adapter endpoint and retain their own mapping records. */
    port vehicleSignal : VehicleSignalAccessPort;
  }

  part def DiagnosticAccessClient :> PhysicalAllocationElement {
    doc /* Candidate physical/software client for diagnostic access through the selected adapter and platform boundary. */
    port diagnostics : DiagnosticAccessPort;
  }

  part def LifecycleClient :> PhysicalAllocationElement {
    doc /* Candidate physical/software client for lifecycle coordination. */
    port lifecycle : LifecycleCoordinationPort;
  }

  part def HealthClient :> PhysicalAllocationElement {
    doc /* Candidate physical/software client for health status observation and forwarding. */
    port health : HealthStatusPort;
  }

  part def UpdateClient :> PhysicalAllocationElement {
    doc /* Candidate physical/software client for update coordination. */
    port update : UpdateCoordinationPort;
  }

  part def ServiceDiscoveryClient :> PhysicalAllocationElement {
    doc /* Candidate physical/software client for service discovery and authorization boundary handling. */
    port discovery : ServiceDiscoveryPort;
  }

  port def VelocityReportPublication :> ROS2TopicPublication {
    out item velocityReport : VelocityReportMessage redefines payload;
  }

  part def AutowareToAAOSSDVAdapterPhysical :> AutowareToAAOSSDVAdapter {
    doc /*
     * Physical adapter candidate with explicit application-side logical ports
     * and AAOS SDV-side service ports. The port contracts are integration
     * boundaries; concrete production ROS 2 topic and VSIDL schemas remain
     * controlled by GAP-MW-019 and GAP-MW-022 until reviewed source revisions
     * are pinned. The typed vehicle-speed port below is a DE4SDV reference
     * contract candidate, not that production binding.
     */
    port applicationSignal : SignalAccessApplicationPort;
    port applicationDiagnostics : DiagnosticApplicationPort;
    port applicationLifecycle : LifecycleApplicationPort;
    port applicationHealth : HealthApplicationPort;
    port applicationUpdate : UpdateApplicationPort;
    port applicationDiscovery : ServiceBindingApplicationPort;

    port aaosSignal : DE4SDVReferenceVehicleSpeedAccessPort;
    port aaosDiagnostics : DiagnosticAccessPort;
    port aaosLifecycle : LifecycleCoordinationPort;
    port aaosHealth : HealthStatusPort;
    port aaosUpdate : UpdateCoordinationPort;
    port aaosDiscovery : ServiceDiscoveryPort;

    port ros2VelocityOut : VelocityReportPublication {
      doc /* Adapter publication to Autoware topic /vehicle/status/velocity_status. */
    }
    port ros2AutowareStateIn : AutowareStateSubscription {
      doc /* Existing Autoware topic /autoware/state. */
    }
    port ros2DiagnosticsOut : DiagnosticPublication {
      doc /* Existing Autoware diagnostic publication /diagnostics. */
    }
  }

  part def AutowareRos2TopicBoundary {
    doc /*
     * Autoware-facing ROS 2 topic boundary for the reference middleware
     * integration slice. Only the velocity-report edge is wired in this
     * increment; the remaining Autoware edges (state, diagnostics) stay
     * candidates owned by GAP-MW-019 and GAP-MW-022 until their contracts
     * are pinned.
     */
    port velocityReportIn : VelocityReportSubscription;
  }

  part def MiddlewarePhysicalSoftwareBoundary {
    doc /*
     * Candidate physical/software integration boundary for an Autoware-to-AAOS
     * SDV configuration. The AAOS model is a boundary reference; no internal
     * implementation, deployment, or runtime claim is made.
     *
     * The wired velocity path reflects the exercised reference rehearsal:
     * AAOS SDV VSIDL service access -> adapter -> Autoware-facing ROS 2
     * velocity-report boundary. Production VSIDL service, FQIN, payload
     * contract, and generated binding remain candidates (GAP-MW-019,
     * GAP-MW-022); the ROS 2 publication boundary is exercised as a
     * VelocityReport-shaped record, not as live ROS 2 runtime evidence.
     *
     * Ownership (owner decisions of 2026-10-23 and 2026-10-25): the
     * boundary refers to the adapter and to the AAOS SDV boundary and owns
     * neither. Both stand for layers of the SDV platform stack: the adapter
     * layer and the guest middleware. In the configured member MW-CONFIG-001,
     * the platform stack owns these layers, and bindings make the references
     * the same things. So the member has one adapter and one AAOS SDV, each
     * with one owner. The AAOS SDV boundary in turn refers to its platform
     * software, which the member binds to the guest operating system of the
     * stack. The physical adapter definition stays a specialization of the
     * adapter definition of the platform stack. The other parts of the
     * boundary are no platform layers, so the boundary owns them. The usage
     * physicalSoftware below is in no product, so its references stay
     * unbound.
     */
    ref part adapter : AutowareToAAOSSDVAdapterPhysical;
    ref part aaosSdvBoundary : SDVCoreBoundary;
    part autowareRos2Boundary : AutowareRos2TopicBoundary;
    part signalAccessClient : SignalAccessClient;
    part diagnosticAccessClient : DiagnosticAccessClient;
    part lifecycleClient : LifecycleClient;
    part healthClient : HealthClient;
    part updateClient : UpdateClient;
    part serviceDiscoveryClient : ServiceDiscoveryClient;

    connection aaosVehicleSpeedToAdapter
      connect aaosSdvBoundary.vehicleSignalAccessOut to adapter.aaosSignal;
    connection adapterToAutowareVelocityReport
      connect adapter.ros2VelocityOut to autowareRos2Boundary.velocityReportIn;

    doc /*
     * AAOS SDV VSIDL service access -> adapter vehicle-speed input. The
     * reference rehearsal exercises this edge through the provider stand-in
     * and the provider-neutral VssVehicleSpeedAdapter; the VSIDL schema and
     * generated client contract are not pinned (GAP-MW-019, GAP-MW-022).
     */
    flow aaosVehicleSpeedToAdapterPayload
      from aaosSdvBoundary.vehicleSignalAccessOut.vehicleSignals
      to adapter.aaosSignal.vehicleSpeed;

    doc /*
     * Adapter VelocityReport publication -> Autoware-facing ROS 2 topic
     * boundary (/vehicle/status/velocity_status). The rehearsal exercises
     * this edge as a VelocityReport-shaped record; live ROS 2 runtime
     * publication is not claimed by this increment.
     */
    flow adapterToAutowareVelocityReportPayload
      from adapter.ros2VelocityOut.velocityReport
      to autowareRos2Boundary.velocityReportIn.velocityReport;
  }

  part def MiddlewarePhysicalSoftwareSourceSet {
    doc /*
     * System 2 source and evidence references used to justify the candidate
     * realization. These records are not physical/software components of the
     * System 1 boundary and therefore remain outside its decomposition.
     */
    ref part aaosSourceArtifact : AAOSSDVSourceArtifact;
    ref part vssVehicleSpeedSource : COVESAVehicleSpeedSemanticSource;
    ref part de4sdvVehicleSpeedAdapterSource : DE4SDVVSSVehicleSpeedAdapterSource;
    ref part referenceInteropBenchSource : DE4SDVAAOSSDVReferenceInteropBenchSource;
    ref part vsidlProviderSource : AAOSVSIDLProviderAgentSource;
    ref part middlewareSource : AAOSMiddlewareSource;
    ref part hardwareInterfacesSource : AAOSHardwareSDVInterfacesSource;
    ref part gatewaySessionSource : AAOSSDVGatewaySessionSource;
    ref part dataTunnelPublicationSource : AAOSSDVDataTunnelPublicationSource;
    ref part rpcAgentSource : AAOSSDVRpcAgentSource;
    ref part lifecycleServiceSource : AAOSLifecycleServiceSource;
    ref part healthMonitorSource : AAOSHealthMonitorSource;
    ref part diagnosticsSource : AAOSDiagnosticsSource;
  }

  part physicalSoftware : MiddlewarePhysicalSoftwareBoundary;
  part physicalSoftwareSources : MiddlewarePhysicalSoftwareSourceSet;

  part aaosBuildRuntimeEnvironmentCandidate : AOSPAAOSBuildRuntimeEnvironment {
    doc /*
     * System 2 enabling-system candidate for the AAOS source/build and
     * Cuttlefish attempt. The bounded campaign used an exercised instance of
     * this capability shape, but provider, region, quota, disk, KVM, and access
     * are not a reusable product or production-deployment selection.
     */
  }

  dependency aaosBuildRuntimeEnablingSystemTrace
    from aaosBuildRuntimeEnvironmentCandidate
    to DE4SDV_ExecutionEnvironments::EngineeringComputeNode;

  /*
   * Bounded Vehicle.Speed campaign communication/deployment slice.
   *
   * This is deliberately separate from physicalSoftware: the two VM domains,
   * host-side forwarder, and private TCP boundary are System 2 evidence
   * infrastructure. The AAOS service bundle emits a structured logcat record;
   * it does not own the network socket in the accepted path because the active
   * guest SELinux policy restricts that service domain. The host-side forwarder
   * owns the private TCP connection instead.
   */
  enum def VehicleSpeedCampaignQuality {
    QUALITY_UNSPECIFIED;
    VALID;
    STALE;
    INVALID;
  }

  item def VehicleSpeedProviderMessage :> DE4SDVReferenceVehicleSpeedPayload {
    doc /*
     * Reference protobuf/VSIDL message published by the generated AAOS
     * Vehicle.Speed provider and consumed by the generated observer.
     * The bounded bridge accepts the VALID quality value for publication;
     * STALE and INVALID remain contract values rejected before publication.
     */
    attribute timestamp_ns : ScalarValues::Integer;
    attribute quality : VehicleSpeedCampaignQuality;
  }

  port def VehicleSpeedProviderPublication {
    out item vehicleSpeed : VehicleSpeedProviderMessage;
  }

  port def VehicleSpeedProviderSubscription {
    in item vehicleSpeed : VehicleSpeedProviderMessage;
  }

  item def VehicleSpeedCampaignWireEnvelope :> VehicleSpeedProviderMessage {
    doc /*
     * Typed campaign envelope emitted by the AAOS observer. The JSON/logcat
     * transport adds `schema` and `clock_domain` to the provider message. The
     * executable JSON/protobuf/VSIDL contracts remain authoritative for exact
     * serialization and validation. The source timestamp remains available in
     * the envelope and bridge logs; the current VelocityReport evidence proves
     * velocity transfer, not source-timestamp propagation through ROS.
     */
    attribute schema : ScalarValues::String;
    attribute clock_domain : ScalarValues::String;
  }

  port def VehicleSpeedCampaignWirePublication {
    out item envelope : VehicleSpeedCampaignWireEnvelope;
  }

  port def VehicleSpeedCampaignWireSubscription {
    in item envelope : VehicleSpeedCampaignWireEnvelope;
  }

  part def AAOSVehicleSpeedProvider {
    doc /*
     * Generated AAOS Vehicle.Speed provider. The provider publishes the
     * reference message through the service-bundle discovery boundary.
     */
    port vehicleSpeedOut : VehicleSpeedProviderPublication;
  }

  part def AAOSVehicleSpeedObserver {
    doc /*
     * Generated independent AAOS Vehicle.Speed observer. It receives the
     * provider message and emits the structured campaign envelope through
     * logcat.
     */
    port vehicleSpeedIn : VehicleSpeedProviderSubscription;
    port structuredLogcatOut : VehicleSpeedCampaignWirePublication;
  }

  part def AAOSVehicleSpeedServiceBundle {
    doc /*
     * AAOS Cuttlefish guest-side provider/observer boundary. The service bundle
     * does not claim direct network-socket ownership.
     */
    part provider : AAOSVehicleSpeedProvider;
    part observer : AAOSVehicleSpeedObserver;
    port structuredLogcatOut : VehicleSpeedCampaignWirePublication;

    connection providerToObserver
      connect provider.vehicleSpeedOut to observer.vehicleSpeedIn;
    flow providerToObserverPayload from provider.vehicleSpeedOut.vehicleSpeed
      to observer.vehicleSpeedIn.vehicleSpeed;
    bind structuredLogcatOut = observer.structuredLogcatOut;
  }

  part def AAOSHostLogcatForwarder {
    doc /*
     * VM-A host-side ADB/logcat extractor and forwarder. It reads the guest's
     * structured record and opens the private TCP connection to the ROS 2 host.
     */
    port structuredLogcatIn : VehicleSpeedCampaignWireSubscription;
    port privateTcpOut : VehicleSpeedCampaignWirePublication;
  }

  part def VehicleSpeedPrivateTcpTransport {
    doc /*
     * Private TCP boundary between independent campaign VM domains. This is
     * development/evidence transport only; it is not native SDV transport or
     * a production vehicle-network decision.
     */
    port vmAIn : VehicleSpeedCampaignWireSubscription;
    port vmBOut : VehicleSpeedCampaignWirePublication;
  }

  part def ROS2VehicleSpeedTcpIngress {
    doc /*
     * VM-B ingress validates the campaign envelope, applies speed_kmh / 3.6,
     * and publishes the official autoware_vehicle_msgs/msg/VelocityReport
     * boundary on /vehicle/status/velocity_status. The conversion is a role-level
     * implementation claim; this deployment view is not a complete internal
     * behavior model of the executable bridge.
     */
    port privateTcpIn : VehicleSpeedCampaignWireSubscription;
    port velocityReportOut : VelocityReportPublication;
  }

  part def ROS2VelocityReportIndependentObserver {
    doc /*
     * Independent VM-B observer of the published VelocityReport. Its
     * observation is separate from the ingress node's conversion and state. It
     * validates the published velocity and records local receipt time; it does
     * not validate source-timestamp propagation.
     */
    port velocityReportIn : VelocityReportSubscription;
  }

  part def AutowareVehicleVelocityConsumer {
    doc /*
     * Real Autoware-side consumer of the published VelocityReport on
     * /vehicle/status/velocity_status. This is the product-path consumption
     * leg: an Autoware node (Autoware vehicle-interface or equivalent) that
     * subscribes to the topic and processes the velocity into its own state
     * and logs, providing Autoware-side provenance (GAP-MW-027 scope).
     *
     * This part is realized by the Autoware runtime on VM-B; it is distinct
     * from the independent observer, which exists only for evidence.
     */
    port velocityReportIn : VelocityReportSubscription;
  }

  part def AAOSVehicleSpeedCampaignHostVm :> AOSPAAOSBuildRuntimeEnvironment {
    doc /*
     * VM-A/System-2 campaign host containing the nested AAOS/Cuttlefish guest
     * and the host-side ADB/logcat forwarder.
     */
    part cuttlefishGuest : AAOSVehicleSpeedServiceBundle;
    part hostForwarder : AAOSHostLogcatForwarder;
  }

  part def ROS2VehicleSpeedCampaignHostVm :> EngineeringExecutionEnvironment {
    doc /*
     * VM-B/System-2 campaign host containing the ROS 2 ingress, independent
     * observer, and the real Autoware vehicle-velocity consumer. It is not a
     * System 1 vehicle compute target.
     */
    part ros2Ingress : ROS2VehicleSpeedTcpIngress;
    part independentObserver : ROS2VelocityReportIndependentObserver;
    part autowareConsumer : AutowareVehicleVelocityConsumer;
  }

  part def VehicleSpeedCampaignCommunicationDeployment {
    doc /*
     * Bounded cross-domain communication path exercised by the reference
     * campaign: AAOS guest -> structured logcat -> VM-A host forwarder ->
     * private TCP -> VM-B ROS 2 ingress -> VelocityReport -> independent
     * observer and real Autoware vehicle-velocity consumer. The deployment is
     * evidence infrastructure, not a production SDV deployment or a direct
     * AAOS-service-to-ROS socket claim. The flows establish typed boundary
     * topology; executable forwarding and conversion semantics remain owned by
     * the implementation and evidence artifacts.
     */
    part vmA : AAOSVehicleSpeedCampaignHostVm;
    part vmB : ROS2VehicleSpeedCampaignHostVm;
    part privateTcpBoundary : VehicleSpeedPrivateTcpTransport;

    connection guestToHostForwarder
      connect vmA.cuttlefishGuest.structuredLogcatOut
      to vmA.hostForwarder.structuredLogcatIn;
    connection hostForwarderToPrivateTcp
      connect vmA.hostForwarder.privateTcpOut to privateTcpBoundary.vmAIn;
    connection privateTcpToRos2Ingress
      connect privateTcpBoundary.vmBOut to vmB.ros2Ingress.privateTcpIn;
    connection ros2IngressToObserver
      connect vmB.ros2Ingress.velocityReportOut
      to vmB.independentObserver.velocityReportIn;
    connection ros2IngressToAutowareConsumer
      connect vmB.ros2Ingress.velocityReportOut
      to vmB.autowareConsumer.velocityReportIn;

    flow guestToHostForwarderPayload
      from vmA.cuttlefishGuest.structuredLogcatOut.envelope
      to vmA.hostForwarder.structuredLogcatIn.envelope;
    flow hostForwarderToPrivateTcpPayload
      from vmA.hostForwarder.privateTcpOut.envelope
      to privateTcpBoundary.vmAIn.envelope;
    flow privateTcpToRos2IngressPayload
      from privateTcpBoundary.vmBOut.envelope
      to vmB.ros2Ingress.privateTcpIn.envelope;
    flow ros2IngressToObserverPayload
      from vmB.ros2Ingress.velocityReportOut.velocityReport
      to vmB.independentObserver.velocityReportIn.velocityReport;
    flow ros2IngressToAutowareConsumerPayload
      from vmB.ros2Ingress.velocityReportOut.velocityReport
      to vmB.autowareConsumer.velocityReportIn.velocityReport;
  }

  part vehicleSpeedCampaignDeployment : VehicleSpeedCampaignCommunicationDeployment;

  dependency vehicleSpeedCampaignImplementationTrace
    from vehicleSpeedCampaignDeployment
    to physicalSoftwareSources::referenceInteropBenchSource;

  allocation def LogicalToPhysicalSoftwareCandidate {
    doc /* Candidate logical-to-physical mapping. This does not imply complete realization, satisfaction, runtime execution, or acceptance. */
  }

  allocation signalTranslatorCandidate : LogicalToPhysicalSoftwareCandidate
    allocate DE4SDV_MiddlewareLogicalArchitecture::system::signalTranslator
    to physicalSoftware::signalAccessClient;
  #AdapterExchangeExcluded allocation vehicleSpeedSystemToSoftwareSignalCandidate : SystemToSoftwareSignalMappingCandidate
    allocate DE4SDV_MiddlewareLogicalArchitecture::system::signalTranslator
    to physicalSoftware::adapter::aaosSignal::vehicleSpeed;
  allocation diagnosticProxyCandidate : LogicalToPhysicalSoftwareCandidate
    allocate DE4SDV_MiddlewareLogicalArchitecture::system::diagnosticProxy
    to physicalSoftware::diagnosticAccessClient;
  allocation lifecycleBridgeCandidate : LogicalToPhysicalSoftwareCandidate
    allocate DE4SDV_MiddlewareLogicalArchitecture::system::lifecycleBridge
    to physicalSoftware::lifecycleClient;
  allocation healthProxyCandidate : LogicalToPhysicalSoftwareCandidate
    allocate DE4SDV_MiddlewareLogicalArchitecture::system::healthProxy
    to physicalSoftware::healthClient;
  allocation updateCoordinatorCandidate : LogicalToPhysicalSoftwareCandidate
    allocate DE4SDV_MiddlewareLogicalArchitecture::system::updateCoordinator
    to physicalSoftware::updateClient;
  allocation serviceBindingManagerCandidate : LogicalToPhysicalSoftwareCandidate
    allocate DE4SDV_MiddlewareLogicalArchitecture::system::serviceBindingManager
    to physicalSoftware::serviceDiscoveryClient;

  dependency aaosBoundaryCandidateForSignalAccess
    from physicalSoftware::signalAccessClient
    to physicalSoftware::aaosSdvBoundary::vsidlMiddleware;
  dependency aaosBoundaryCandidateForDiagnostics
    from physicalSoftware::diagnosticAccessClient
    to physicalSoftware::aaosSdvBoundary::diagnostics;
  dependency aaosBoundaryCandidateForLifecycle
    from physicalSoftware::lifecycleClient
    to physicalSoftware::aaosSdvBoundary::lifecycleManager;
  dependency aaosBoundaryCandidateForHealth
    from physicalSoftware::healthClient
    to physicalSoftware::aaosSdvBoundary::healthMonitor;
  dependency aaosBoundaryCandidateForUpdates
    from physicalSoftware::updateClient
    to physicalSoftware::aaosSdvBoundary::updateManager;
  dependency aaosBoundaryCandidateForDiscovery
    from physicalSoftware::serviceDiscoveryClient
    to physicalSoftware::aaosSdvBoundary::serviceDiscovery;

  dependency adapterCandidateAtApplicationBoundary
    from physicalSoftware::adapter
    to DE4SDV_MiddlewareLogicalArchitecture::system;

  #AdapterExchangeExcluded dependency adapterSignalMapping
    from physicalSoftware::adapter::applicationSignal
    to physicalSoftware::adapter::aaosSignal;
  dependency referenceVehicleSpeedContractTrace
    from physicalSoftware::adapter::aaosSignal::vehicleSpeed
    to physicalSoftwareSources::referenceInteropBenchSource;
  dependency referenceVehicleSpeedVSIDLCandidate
    from physicalSoftware::adapter::aaosSignal::vehicleSpeed
    to physicalSoftware::aaosSdvBoundary::vsidlMiddleware;
  #AdapterExchangeExcluded dependency adapterDiagnosticMapping
    from physicalSoftware::adapter::applicationDiagnostics
    to physicalSoftware::adapter::aaosDiagnostics;
  #AdapterExchangeExcluded dependency adapterLifecycleMapping
    from physicalSoftware::adapter::applicationLifecycle
    to physicalSoftware::adapter::aaosLifecycle;
  #AdapterExchangeExcluded dependency adapterHealthMapping
    from physicalSoftware::adapter::applicationHealth
    to physicalSoftware::adapter::aaosHealth;
  #AdapterExchangeExcluded dependency adapterUpdateMapping
    from physicalSoftware::adapter::applicationUpdate
    to physicalSoftware::adapter::aaosUpdate;
  #AdapterExchangeExcluded dependency adapterDiscoveryMapping
    from physicalSoftware::adapter::applicationDiscovery
    to physicalSoftware::adapter::aaosDiscovery;

  dependency adapterSignalServiceCandidate
    from physicalSoftware::adapter::aaosSignal
    to physicalSoftware::aaosSdvBoundary::vsidlMiddleware;
  dependency adapterDiagnosticServiceCandidate
    from physicalSoftware::adapter::aaosDiagnostics
    to physicalSoftware::aaosSdvBoundary::diagnostics;
  dependency adapterLifecycleServiceCandidate
    from physicalSoftware::adapter::aaosLifecycle
    to physicalSoftware::aaosSdvBoundary::lifecycleManager;
  dependency adapterHealthServiceCandidate
    from physicalSoftware::adapter::aaosHealth
    to physicalSoftware::aaosSdvBoundary::healthMonitor;
  dependency adapterUpdateServiceCandidate
    from physicalSoftware::adapter::aaosUpdate
    to physicalSoftware::aaosSdvBoundary::updateManager;
  dependency adapterDiscoveryServiceCandidate
    from physicalSoftware::adapter::aaosDiscovery
    to physicalSoftware::aaosSdvBoundary::serviceDiscovery;

  dependency vsidlSignalToROS2Velocity
    from physicalSoftware::adapter::aaosSignal::vehicleSpeed
    to physicalSoftware::adapter::ros2VelocityOut;
  #AdapterExchangeExcluded dependency ros2AutowareStateToVSIDLLifecycle
    from physicalSoftware::adapter::ros2AutowareStateIn
    to physicalSoftware::adapter::aaosLifecycle;
  #AdapterExchangeExcluded dependency vsidlDiagnosticsToROS2Diagnostics
    from physicalSoftware::adapter::aaosDiagnostics
    to physicalSoftware::adapter::ros2DiagnosticsOut;

  dependency vehicleSpeedSemanticTrace
    from physicalSoftware::adapter::aaosSignal::vehicleSpeed
    to physicalSoftwareSources::vssVehicleSpeedSource;
  dependency de4sdvAdapterImplementationTrace
    from physicalSoftware::adapter
    to physicalSoftwareSources::de4sdvVehicleSpeedAdapterSource;
  dependency referenceInteropBenchTrace
    from physicalSoftware::adapter
    to physicalSoftwareSources::referenceInteropBenchSource;
  dependency aaosVSIDLSourceTrace
    from physicalSoftware::adapter::aaosSignal
    to physicalSoftwareSources::vsidlProviderSource;
  dependency aaosMiddlewareSourceTrace
    from physicalSoftware::adapter::aaosSignal
    to physicalSoftwareSources::middlewareSource;
  dependency aaosHardwareInterfacesSourceTrace
    from physicalSoftware::adapter::aaosSignal
    to physicalSoftwareSources::hardwareInterfacesSource;
  dependency aaosGatewaySessionSourceTrace
    from physicalSoftware::adapter::aaosSignal
    to physicalSoftwareSources::gatewaySessionSource;
  dependency aaosDataTunnelSourceTrace
    from physicalSoftware::adapter::aaosSignal
    to physicalSoftwareSources::dataTunnelPublicationSource;
  dependency aaosRpcAgentSourceTrace
    from physicalSoftware::adapter::aaosSignal
    to physicalSoftwareSources::rpcAgentSource;
  dependency aaosLifecycleSourceTrace
    from physicalSoftware::aaosSdvBoundary::lifecycleManager
    to physicalSoftwareSources::lifecycleServiceSource;
  dependency aaosHealthSourceTrace
    from physicalSoftware::aaosSdvBoundary::healthMonitor
    to physicalSoftwareSources::healthMonitorSource;
  dependency aaosDiagnosticsSourceTrace
    from physicalSoftware::aaosSdvBoundary::diagnostics
    to physicalSoftwareSources::diagnosticsSource;
  dependency aaosAdapterSourceManifestTrace
    from physicalSoftware::adapter
    to physicalSoftwareSources::aaosSourceArtifact;
  dependency aaosSourceBuildEnvironmentCandidate
    from physicalSoftwareSources::aaosSourceArtifact
    to aaosBuildRuntimeEnvironmentCandidate;
  dependency aaosCuttlefishEnvironmentCandidate
    from physicalSoftware::aaosSdvBoundary
    to aaosBuildRuntimeEnvironmentCandidate;

  concern physicalStructureConcern : PhysicalStructureConcern {
    doc /*
     * Review the System 1 candidate software boundary: adapter, AAOS SDV
     * boundary, and application-side clients. Source records and the bounded
     * System 2 campaign are excluded from this breakdown.
     */
    subject;
    stakeholder systemsEngineer : SystemsEngineer;
    stakeholder reviewer : OpenSourceReviewer;
  }

  concern physicalInterfaceConcern : PhysicalInterfaceConcern {
    doc /*
     * Known issue: no System 1 Physical Interface view is published yet.
     * Physical interfaces can include software protocol endpoints, but this
     * increment has only a candidate vehicle-speed access port and no reviewed
     * pin, bus, deployed service, or production transport contract. The source
     * definitions remain authoritative; publishing their current native
     * projection would duplicate the functional interface catalog and leak an
     * unrelated candidate allocation.
     */
    subject;
    stakeholder systemsEngineer : SystemsEngineer;
    stakeholder reviewer : OpenSourceReviewer;
  }

  concern vehicleSpeedCampaignInternalExchangeConcern : PhysicalInternalExchangeConcern {
    doc /*
     * Known issue: no Physical Internal Exchange view is published for the
     * campaign. Five explicit connections and five named item flows remain
     * authoritative in the model, but the tested native projection renders
     * only nested part boxes and does not materialize the connector path, flow
     * direction, or exchanged item types. A box-only artifact would misstate
     * the concern. The campaign source and observer are both inside the subject,
     * so there is also no external boundary exchange to substitute.
     */
    subject campaignDeployment : VehicleSpeedCampaignCommunicationDeployment;
    stakeholder systemsEngineer : SystemsEngineer;
    stakeholder reviewer : OpenSourceReviewer;
    stakeholder systemArchitect : SystemArchitect;
    stakeholder softwareDeveloper : SoftwareDeveloper;
    stakeholder verificationEngineer : VerificationEngineer;
  }

  concern vehicleSpeedServiceBundleInternalExchangeConcern : PhysicalInternalExchangeConcern {
    doc /*
     * Which provider sends VehicleSpeedProviderMessage to which observer,
     * through which owned ports and connector, and in which direction? Keep
     * this bounded review slice inside the AAOS service bundle; transport and
     * deployment topology belong to the wider campaign concern.
     */
    subject serviceBundle : AAOSVehicleSpeedServiceBundle;
    stakeholder systemsEngineer : SystemsEngineer;
    stakeholder reviewer : OpenSourceReviewer;
    stakeholder softwareDeveloper : SoftwareDeveloper;
    stakeholder verificationEngineer : VerificationEngineer;
  }

  concern vehicleSpeedCampaignStructureConcern : PhysicalStructureConcern {
    doc /* Supporting System 2 campaign-host breakdown, distinct from the System 1 product boundary. */
    subject campaignDeployment : VehicleSpeedCampaignCommunicationDeployment;
    stakeholder systemsEngineer : SystemsEngineer;
    stakeholder reviewer : OpenSourceReviewer;
  }

  concern vehicleSpeedCampaignInterfaceConcern : PhysicalInterfaceConcern {
    doc /* Supporting System 2 campaign transport contracts, distinct from the System 1 candidate interfaces. */
    subject campaignDeployment : VehicleSpeedCampaignCommunicationDeployment;
    stakeholder systemsEngineer : SystemsEngineer;
    stakeholder reviewer : OpenSourceReviewer;
  }

  concern physicalFunctionalMappingConcern : PhysicalFunctionalMappingConcern {
    subject;
    stakeholder systemsEngineer : SystemsEngineer;
    stakeholder reviewer : OpenSourceReviewer;
  }

  concern physicalLogicalMappingConcern : PhysicalLogicalMappingConcern {
    subject;
    stakeholder systemsEngineer : SystemsEngineer;
    stakeholder reviewer : OpenSourceReviewer;
  }

  view middlewarePhysicalStructureView {
    viewpoint selectedPhysicalStructureViewpoint : PhysicalStructureDefinitionViewpoint {
      frame physicalStructureConcern;
    }
    expose MiddlewarePhysicalSoftwareBoundary;
    attribute depth = 1;
    attribute showAnnotationRows = false;
    attribute maxCompartmentEntries = -1;
    render asTreeDiagram;
  }

  metadata def AdapterExchangeExcluded {
    doc /*
     * View-scope exclusion tag for the adapter-exchange concern. Relationships
     * annotated with this metadata describe candidate paths outside the wired
     * velocity exchange (state, diagnostics, lifecycle, health, update,
     * discovery mappings) and are filtered out of middlewareAdapterBoundaryExchangeView.
     */
  }

  concern adapterBoundaryExchangeConcern : PhysicalInternalExchangeConcern {
    doc /*
     * Which AAOS SDV VSIDL service access feeds the adapter, and which
     * Autoware-facing ROS 2 velocity-report boundary does the adapter
     * publish through, in which direction? Keep this bounded to the wired
     * velocity path; state and diagnostics edges remain candidates.
     */
    subject boundary : MiddlewarePhysicalSoftwareBoundary;
    stakeholder systemsEngineer : SystemsEngineer;
    stakeholder reviewer : OpenSourceReviewer;
    stakeholder softwareDeveloper : SoftwareDeveloper;
    stakeholder verificationEngineer : VerificationEngineer;
  }

  view middlewareAdapterBoundaryExchangeView {
    viewpoint selectedAdapterBoundaryExchangeViewpoint : PhysicalInternalExchangeViewpoint {
      frame adapterBoundaryExchangeConcern;
    }
    doc /*
     * Bounded projection of the wired adapter chain: AAOS SDV service
     * access -> adapter -> Autoware-facing ROS 2 velocity-report boundary.
     * Parts are wired through ports; inherited port rows, mapping
     * dependencies, and allocations are excluded from this concern.
     */
    expose MiddlewarePhysicalSoftwareBoundary::adapter;
    expose MiddlewarePhysicalSoftwareBoundary::adapter::**;
    expose MiddlewarePhysicalSoftwareBoundary::aaosSdvBoundary;
    expose MiddlewarePhysicalSoftwareBoundary::autowareRos2Boundary;
    expose MiddlewarePhysicalSoftwareBoundary::autowareRos2Boundary::*;
    filter not (@ AdapterExchangeExcluded);
    attribute depth = -1;
    attribute showAnnotationRows = false;
    attribute showInheritedRows = false;
    attribute maxCompartmentEntries = 0;
    render asInterconnectionDiagram;
  }

  /*
   * No Physical Context Exchange view is published for this campaign. Both
   * hosts and the complete one-directional transfer chain are contained by the
   * deployment subject, so presenting them as an external-boundary exchange
   * would be false. The typed connections and flows in the source are
   * authoritative for this scope while native rendering remains inadequate.
   */

  view middlewareAAOSVehicleSpeedServiceBundleInternalExchangeView {
    viewpoint selectedAAOSVehicleSpeedServiceBundleInternalExchangeViewpoint : PhysicalInternalExchangeViewpoint {
      frame vehicleSpeedServiceBundleInternalExchangeConcern;
    }
    doc /*
     * Bounded native projection of the authoritative provider-to-observer
     * connection and VehicleSpeedProviderMessage flow. The wider campaign
     * exchange remains withheld because it does not pass the same visual gate.
     */
    expose vehicleSpeedCampaignDeployment::vmA::cuttlefishGuest;
    expose vehicleSpeedCampaignDeployment::vmA::cuttlefishGuest::**;
    attribute depth = -1;
    attribute showAnnotationRows = false;
    render asInterconnectionDiagram;
  }

  view middlewareVehicleSpeedCampaignStructureView {
    viewpoint selectedVehicleSpeedCampaignStructureViewpoint : PhysicalStructureDefinitionViewpoint {
      frame vehicleSpeedCampaignStructureConcern;
    }
    doc /*
     * Supporting structure view for the two independent System 2 hosts, the
     * nested AAOS guest, host-side forwarder, ROS 2 ingress, and observer.
     */
    expose VehicleSpeedCampaignCommunicationDeployment;
    expose VehicleSpeedCampaignCommunicationDeployment::vmA;
    expose VehicleSpeedCampaignCommunicationDeployment::vmA::cuttlefishGuest;
    expose VehicleSpeedCampaignCommunicationDeployment::vmA::hostForwarder;
    expose VehicleSpeedCampaignCommunicationDeployment::privateTcpBoundary;
    expose VehicleSpeedCampaignCommunicationDeployment::vmB;
    expose VehicleSpeedCampaignCommunicationDeployment::vmB::ros2Ingress;
    expose VehicleSpeedCampaignCommunicationDeployment::vmB::independentObserver;
    attribute showAnnotationRows = false;
    attribute maxCompartmentEntries = 0;
    render asTreeDiagram;
  }

  view middlewareVehicleSpeedCampaignInterfaceView {
    viewpoint selectedVehicleSpeedCampaignInterfaceViewpoint : PhysicalInterfaceDefinitionViewpoint {
      frame vehicleSpeedCampaignInterfaceConcern;
    }
    doc /*
     * Supporting interface view for the campaign envelope and the official
     * VelocityReport publication/subscription boundary. Exact serialization
     * and transport parameters remain owned by the executable contracts.
     */
    expose VehicleSpeedProviderPublication;
    expose VehicleSpeedProviderSubscription;
    expose VehicleSpeedCampaignWirePublication;
    expose VehicleSpeedCampaignWireSubscription;
    expose VelocityReportPublication;
    expose VelocityReportSubscription;
    attribute showAnnotationRows = false;
    render asTreeDiagram;
  }

  /*
   * No physical-function allocation is modeled in this increment. Publishing a
   * Physical Functional Mapping view would therefore present package contents
   * as a false mapping. Add the view only when physical actions and their
   * allocations exist in the model.
   */

  view middlewarePhysicalLogicalMappingView : MVD::MatrixView {
    viewpoint selectedPhysicalLogicalMappingViewpoint : PhysicalLogicalMappingViewpoint {
      frame physicalLogicalMappingConcern;
    }
    view :>> rowView {
      expose system::signalTranslator;
      expose system::diagnosticProxy;
      expose system::lifecycleBridge;
      expose system::healthProxy;
      expose system::updateCoordinator;
      expose system::serviceBindingManager;
      attribute :>> representation = Rep::name;
    }
    view :>> columnView {
      expose physicalSoftware::signalAccessClient;
      expose physicalSoftware::diagnosticAccessClient;
      expose physicalSoftware::lifecycleClient;
      expose physicalSoftware::healthClient;
      expose physicalSoftware::updateClient;
      expose physicalSoftware::serviceDiscoveryClient;
      expose physicalSoftware::adapter::aaosSignal::vehicleSpeed;
      attribute :>> representation = Rep::name;
    }
    view :>> cellView {
      expose DE4SDV_MiddlewarePhysicalSoftwareRealization::*;
      attribute :>> direction = SysideViews::MatrixTraceabilityDirection::row2col;
    }
  }
}
