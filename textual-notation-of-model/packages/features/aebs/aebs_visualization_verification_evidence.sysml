/*
 * DE4SDV INC-AEBS-010 Phase 10 verification and evidence model slice.
 *
 * This slice is the Phase 10 V&V portion of the INC-AEBS-010 visualization
 * chain. It defines the verification cases, retained evidence records,
 * bounded assurance claim, deferred counterclaims, and claim-boundary
 * semantics for the System 2 read-only AEBS forward-situation visualization
 * test system.
 *
 * Success criteria belong to the requirements: each design-input requirement
 * states them in its successCriteria attribute (INCOSE A6; owner decision
 * 2026-10-10), and each verification case verifies the requirements whose
 * success criteria it checks. The former acceptance criteria AC-AEBS-S2-001
 * to AC-AEBS-S2-008 are retired. AC-AEBS-S2-008, the evidence-integrity rule
 * of every case, is now the obligation of the shared evidence record
 * RetainedVisualizationEvidence. The claim, arguments and counter-claims are
 * assurance artifacts (the assurance argumentation kinds of
 * DE4SDV_MethodContext), outside the requirement lineage.
 *
 * It consumes the retained evidence committed by the implementation campaign
 * (implementation/aebs-aaos-sdv-visualization-bench/evidence/010/). Every
 * evidence part below names the exact retained artifact; the dispositions
 * follow the evidence ladder vocabulary (observed_bounded /
 * deferred_not_proven / not_claimed) with scenario-safety outcome explicitly
 * deferred_not_proven. No safety, certification, homologation,
 * production-readiness, or vehicle-command claim is made or implied.
 *
 * Package name note: the visualization chain increment ID is INC-AEBS-010,
 * and this slice is its Phase 10 V&V evidence record
 * (DE4SDV_AEBSVisualizationVerificationEvidence). The package drops the
 * increment number per naming-conventions.md section 7: it is the enduring
 * canonical verification-evidence model of the visualization concern; the
 * increment identity stays owned by the framing slice (incAEBS010).
 */

package DE4SDV_AEBSVisualizationVerificationEvidence {
  private import DE4SDV_MethodContext::*;
  private import DE4SDV_ProductLine::*;
  private import DE4SDV_Stakeholders::*;
  private import DE4SDV_ExecutionEnvironments::*;
  private import DE4SDV_AEBSVisualizationFraming::*;
  private import DE4SDV_AEBSVisualizationNeedsRequirements::*;
  private import DE4SDV_AEBSVisualizationPhysicalSoftwareRealization::*;
  private import DE4SDV_AEBSVisualizationVariabilityConfiguration::*;
  private import VerificationCases::*;
  private import VerificationMethodKind::*;
  private import ScalarValues::*;
  private import SAF_Viewpoints::*;
  private import Views::*;

  /*
   * INC-AEBS-010 increment identity: owned by the canonical framing slice
   * (DE4SDV_AEBSVisualizationFraming::incAEBS010). This evidence slice is
   * bounded Phase 10 V&V content for that increment, not a second increment
   * identity; visualizationVerificationSystem below carries the slice's trace.
   */
  references incAEBS010;

  /* ──────────────────────────────────────────
   * Evidence vocabulary and observation records
   * ────────────────────────────────────────── */

  enum def VisualizationScenario {
    liveChainCorrelation;
    lifecycleArc;
    readOnlyBoundary;
    provenanceSeparation;
    failClosedStaleness;
    degradedStateRendering;
    restorationBehavior;
    liveSourceFidelity;
    staleAndInvalidFrames;
    renderingEnvironment;
  }

  enum def VisualizationEvidenceDisposition {
    planned;
    observedBounded;
    observedUnidentifiedBuild;
    contradictedByRetainedData;
    partial;
    blocked;
    notClaimed;
  }

  item def VisualizationObservation {
    attribute callbackCount : ScalarValues::Integer;
    attribute sequenceSpan : ScalarValues::String;
    attribute observedRateHz : ScalarValues::Real;
    attribute gapCount : ScalarValues::Integer;
    attribute independentCapture : Boolean;
  }

  item def RetainedVisualizationEvidence {
    doc /*
     * The retained evidence record that every visualization verification case
     * collects, and the home of the evidence-integrity and claim-boundary
     * obligation of every case (formerly AC-AEBS-S2-008; an obligation of the
     * cases, not a success criterion of any requirement). A retained verdict
     * is acceptable only when its record binds the configured test article,
     * execution environment, wire contract, raw observation artifacts, and
     * independent observer identities. Missing evidence is recorded as
     * planned, partial, blocked, or not claimed, never as an observed runtime
     * pass. MapVisualizationOutcomeToVerdict applies the second sentence.
     * This home was chosen during the INC-AEBS-010 walk and is open to owner
     * review; a kernel-level evidence-integrity rule could follow as a method
     * change.
     */
    attribute configurationIdentity : ScalarValues::String;
    attribute executionEnvironmentIdentity : ScalarValues::String;
    attribute contractIdentity : ScalarValues::String;
    attribute rawObservationArtifact : ScalarValues::String;
    attribute independentObserverIdentity : ScalarValues::String;
    attribute disposition : VisualizationEvidenceDisposition;
    attribute claimBoundary : ScalarValues::String;
  }

  item def ReplayedVisualizationEvaluation {
    attribute scenario : VisualizationScenario;
    attribute outcome : VisualizationEvidenceDisposition;
    attribute acceptanceSummary : ScalarValues::String;
  }

  /*
   * Verdict mapping: only observedBounded evidence produces pass. partial
   * maps to inconclusive — a partial observation cannot upgrade into an
   * acceptance claim without a separately justified bounded-pass
   * interpretation (none exists for the retained campaign).
   * observedUnidentifiedBuild (observed on a build that is not exactly
   * identified, GAP-AEBS-010-009) falls to inconclusive; by owner decision
   * of 2026-10-09 no re-capture is planned, so it stays inconclusive.
   * contradictedByRetainedData (an evidence statement that the retained data
   * itself contradicts, GAP-AEBS-010-009) also falls to inconclusive: the
   * contradiction defeats the record, it does not show the requirement
   * failed.
   */
  calc def MapVisualizationOutcomeToVerdict {
    in outcome : VisualizationEvidenceDisposition;
    return verdict : VerdictKind =
      if outcome == VisualizationEvidenceDisposition::observedBounded? VerdictKind::pass
      else if outcome == VisualizationEvidenceDisposition::partial? VerdictKind::inconclusive
      else if outcome == VisualizationEvidenceDisposition::blocked? VerdictKind::inconclusive
      else if outcome == VisualizationEvidenceDisposition::notClaimed? VerdictKind::inconclusive
      else VerdictKind::inconclusive;
  }

  /* ──────────────────────────────────────────
   * Verification bench (System 1 unchanged / System 2 instrument)
   * ────────────────────────────────────────── */

  part def VisualizationVerificationBench {
    doc /*
     * System 1 is the configured member executing unchanged AEBS behavior:
     * the uninstrumented AAOS-integrated Autoware member governed by the
     * accepted product-line scope. System 2 is the visualization test system
     * and its campaign environment — the instrumented test article plus
     * observation instrumentation; it is not a product selection. The
     * instrument observes System 1 read-only and issues no vehicle command.
     */
    /* System 1 subject: uninstrumented configured member (scope member). */
    part system1MemberProduct : DE4SDV_MiddlewareVariabilityConfiguration::MiddlewareAutowareAAOSSDVConfiguredMember;
    /* Configuration role: the configured test article AEBS-CONFIG-010-001. */
    part system2TestArticle :> testArticle;
    /* Subject role: the visualization test system as realized in that article; the verified design-input requirements bind to it. */
    ref part system2Instrument :> system2VisualizationInstrument = system2TestArticle.visualizationChain.instrument;
    attribute scenario : VisualizationScenario;
  }

  part liveChainCorrelationBench : VisualizationVerificationBench {
    attribute :>> scenario = VisualizationScenario::liveChainCorrelation;
  }
  part lifecycleArcBench : VisualizationVerificationBench {
    attribute :>> scenario = VisualizationScenario::lifecycleArc;
  }
  part readOnlyBoundaryBench : VisualizationVerificationBench {
    attribute :>> scenario = VisualizationScenario::readOnlyBoundary;
  }
  part provenanceSeparationBench : VisualizationVerificationBench {
    attribute :>> scenario = VisualizationScenario::provenanceSeparation;
  }
  part failClosedStalenessBench : VisualizationVerificationBench {
    attribute :>> scenario = VisualizationScenario::failClosedStaleness;
  }
  part degradedStateRenderingBench : VisualizationVerificationBench {
    attribute :>> scenario = VisualizationScenario::degradedStateRendering;
  }
  part restorationBehaviorBench : VisualizationVerificationBench {
    attribute :>> scenario = VisualizationScenario::restorationBehavior;
  }
  part liveSourceFidelityBench : VisualizationVerificationBench {
    attribute :>> scenario = VisualizationScenario::liveSourceFidelity;
  }
  part staleAndInvalidFramesBench : VisualizationVerificationBench {
    attribute :>> scenario = VisualizationScenario::staleAndInvalidFrames;
  }
  part renderingEnvironmentBench : VisualizationVerificationBench {
    attribute :>> scenario = VisualizationScenario::renderingEnvironment;
  }

  /* ──────────────────────────────────────────
   * Success criteria: requirement attributes, not separate elements
   * ────────────────────────────────────────── */

  /* Success criteria are part of the requirement (INCOSE A6, attribute
   * successCriteria in DE4SDV_AEBSVisualizationNeedsRequirements).
   * The seven requirement-specific criteria AC-AEBS-S2-001..007 moved there,
   * one to one, and their IDs are retired; REQ-AEBS-S2-015..018, -020 and -021
   * state their success criteria there directly.
   * AC-AEBS-S2-008 moved to RetainedVisualizationEvidence, a home chosen
   * during the walk and open to owner review. The success criteria
   * of REQ-AEBS-S2-015..018, -020 and -021 were formalized after the retained
   * take: each case that verifies them holds a related observation made under
   * the former criterion wording, but none is assessed against them, and no
   * case verdict covers them. */

  /* ──────────────────────────────────────────
   * Retained evidence records (exact artifacts in the implementation bench)
   * ────────────────────────────────────────── */

  part liveChainEvidence : RetainedVisualizationEvidence {
    doc /*
     * EVID-AEBS-S2-001. Retained live-chain correlation evidence for the
     * corrected final campaign (2026-09-01): 1090 consecutive app-side
     * onGatewayFrame callbacks, sequence span 22891-23980, zero gaps, 10 Hz,
     * mirrored by ingress-side publishes over the chain pinned Autoware AEB
     * f603d8759c92fb2f423f1544844e13086d79ad09 -> ROS bridge frame assembler
     * -> TCP frame server :4721 -> adb reverse -> native ingress -> Gateway
     * Data Tunnel topic aebs-visualization-frame (schema v1.1) -> app
     * onGatewayFrame. Observer pass_observed_chain, exit 0, 1597
     * observations, 0 errors.
     */
    attribute :>> configurationIdentity = "AEBS-CONFIG-010-001";
    attribute :>> executionEnvironmentIdentity = "gcp-europe-west4-a de4sdv-aaos-build, sdv_ivi_cf guest, corrected final generation";
    attribute :>> contractIdentity = "interface/aebs_visualization.proto schema v1.1, topic aebs-visualization-frame";
    attribute :>> rawObservationArtifact = "implementation/aebs-aaos-sdv-visualization-bench/evidence/010/forward-ui/final-hmi-v21-corrected/app-ingress-frame.log";
    attribute :>> independentObserverIdentity = "scenario_observer (pass_observed_chain, 1597 observations, 0 errors)";
    attribute :>> disposition = VisualizationEvidenceDisposition::observedUnidentifiedBuild;
    attribute :>> claimBoundary = "Live observation-chain evidence on the bench deployment, a scoped observation on a build derived from 4d8dc1b that is not exactly identified (GAP-AEBS-010-009; no re-capture planned, owner decision 2026-10-09); not verification of the configured test article, and not safety, braking-authority, certification, or production evidence.";
  }

  part lifecycleArcEvidence : RetainedVisualizationEvidence {
    doc /*
     * EVID-AEBS-S2-002. Retained continuous-take lifecycle evidence: one
     * uninterrupted 70.15 s screenrecord of the corrected final UI
     * generation covering MONITORING 0-10 s, WARNING ~10-11.5 s (24 obstacle
     * points, no braking), INTERVENTION ~11.5-14 s (braking latched), and
     * RELEASED from ~14 s, entered at ego speed 0.0 m/s (seq 23034).
     * The take's segment record states that the ego does not re-accelerate
     * after release, so no post-release re-approach is shown. The take's own
     * frame log contradicts that: the ego speed rises from seq 23036 and
     * holds 6.876 m/s from seq 23091 to the end of the log (seq 23980), the
     * display-derived closest-point range closes from about 8.8 m to under
     * 0.01 m, and RELEASED (released_verified_stop) with braking=true
     * persists on all 947 RELEASED frames. The independent observer's 6.31 s
     * window ended at release. The verified-stop reading of the RELEASED
     * period is therefore contradicted by the retained data; no re-capture
     * is planned (owner decision 2026-10-09, GAP-AEBS-010-009). Release
     * relation recorded as
     * release_while_native_diagnostic_retained; scenario-safety outcome
     * remains deferred_not_proven. The approved
     * publication cut composes a 3 s title card, the untouched 0-20 s of this
     * take, and a 3 s end card; the cards are editing frames, not app output.
     */
    attribute :>> configurationIdentity = "AEBS-CONFIG-010-001";
    attribute :>> executionEnvironmentIdentity = "gcp-europe-west4-a de4sdv-aaos-build, sdv_ivi_cf guest, corrected final generation";
    attribute :>> contractIdentity = "screenrecord display 0, 1080x600";
    attribute :>> rawObservationArtifact = "implementation/aebs-aaos-sdv-visualization-bench/evidence/010/forward-ui/final-hmi-v21-corrected/raw-continuous.mp4";
    attribute :>> independentObserverIdentity = "scenario_observer state boundary extraction (segment.yaml)";
    attribute :>> disposition = VisualizationEvidenceDisposition::contradictedByRetainedData;
    attribute :>> claimBoundary = "One continuous take of the corrected generation on a build that is not exactly identified; its verified-stop reading of the RELEASED period is contradicted by the take's own frame log (GAP-AEBS-010-009; no re-capture planned, owner decision 2026-10-09); title/end cards are editing frames; not safety or certification evidence.";
  }

  part readOnlyBoundaryEvidence : RetainedVisualizationEvidence {
    doc /*
     * EVID-AEBS-S2-003. Read-only boundary evidence: the wire contract carries
     * no command path, the bridge subscribes only (no publishers, no
     * services, no actions), the ingress publishes into the Gateway Data
     * Tunnel only, and the provenance ribbon is present in every retained
     * public frame. Enforced additionally by the presentation-contract guard
     * tests in the repository test suite.
     */
    attribute :>> configurationIdentity = "AEBS-CONFIG-010-001";
    attribute :>> executionEnvironmentIdentity = "repository test suite + retained campaign artifacts";
    attribute :>> contractIdentity = "implementation/aebs-aaos-sdv-visualization-bench/interface/aebs_visualization.proto";
    attribute :>> rawObservationArtifact = "implementation/aebs-aaos-sdv-visualization-bench/evidence/010/forward-ui/final-hmi-v21-corrected/state-monitoring.png";
    attribute :>> independentObserverIdentity = "tests/test_aebs_visualization_hmi_presentation_contract.py + bridge non-interference tests";
    attribute :>> disposition = VisualizationEvidenceDisposition::observedUnidentifiedBuild;
    attribute :>> claimBoundary = "Structural and rendered-session read-only evidence; the rendered session ran on a build derived from 4d8dc1b that is not exactly identified (GAP-AEBS-010-009; no re-capture planned, owner decision 2026-10-09); no vehicle-interaction behavior is exercised or claimed.";
  }

  part provenanceSeparationEvidence : RetainedVisualizationEvidence {
    doc /*
     * EVID-AEBS-S2-004. Display-derived versus native decision semantics
     * separation evidence for the corrected generation: no
     * Target range / AEB braking threshold pair or RSS reference line is
     * rendered anywhere in the retained stills or UI dumps, obstacle geometry
     * is drawn only from the filtered cloud in base_link, and the
     * engineering-status panel states that AEB decision distances are not
     * visualized. Verified pre-recording against guest UI dumps and after by
     * visual review of the retained stills.
     */
    attribute :>> configurationIdentity = "AEBS-CONFIG-010-001";
    attribute :>> executionEnvironmentIdentity = "gcp-europe-west4-a de4sdv-aaos-build, sdv_ivi_cf guest, corrected final generation";
    attribute :>> contractIdentity = "implementation/aebs-aaos-sdv-visualization-bench/VISUALIZATION-CONTRACT.md section 3 removal list";
    attribute :>> rawObservationArtifact = "implementation/aebs-aaos-sdv-visualization-bench/evidence/010/forward-ui/final-hmi-v21-corrected/state-warning.png";
    attribute :>> independentObserverIdentity = "tests/test_aebs_visualization_hmi_presentation_contract.py";
    attribute :>> disposition = VisualizationEvidenceDisposition::observedUnidentifiedBuild;
    attribute :>> claimBoundary = "Presentation-separation evidence for the corrected generation, a scoped observation on a build derived from 4d8dc1b that is not exactly identified (GAP-AEBS-010-009; no re-capture planned, owner decision 2026-10-09); not a claim about native Autoware AEB decision internals.";
  }

  part failClosedStalenessEvidence : RetainedVisualizationEvidence {
    doc /*
     * EVID-AEBS-S2-005. Staleness observation: within the retained take the
     * display-derived obstacle geometry (range, bearing, points) was cleared
     * while accepted live frames continued, at seq 23032 with the ego
     * stopped and braking latched, and at seq 23091 with the ego at
     * 6.876 m/s after the range had closed to under 0.01 m. Whether the
     * filtered obstacle-cloud source had stopped updating, the trigger the
     * success criteria of REQ-AEBS-S2-019 name (formerly AC-AEBS-S2-005), or
     * delivered an empty cloud is not established:
     * the HMI log cannot tell them apart, and no host-side bridge record was
     * retained (GAP-AEBS-010-009). No interpolation or prediction
     * substituted for missing fresh data.
     */
    attribute :>> configurationIdentity = "AEBS-CONFIG-010-001";
    attribute :>> executionEnvironmentIdentity = "gcp-europe-west4-a de4sdv-aaos-build, sdv_ivi_cf guest, corrected final generation";
    attribute :>> contractIdentity = "frame assembler receipt-based staleness bound (bridge source)";
    attribute :>> rawObservationArtifact = "implementation/aebs-aaos-sdv-visualization-bench/evidence/010/forward-ui/final-hmi-v21-corrected/segment.yaml";
    attribute :>> independentObserverIdentity = "app-ingress-frame.log field-level observation";
    attribute :>> disposition = VisualizationEvidenceDisposition::observedUnidentifiedBuild;
    attribute :>> claimBoundary = "Geometry cleared while frames continued, observed within one take on a build that is not exactly identified; the cloud-silence trigger is not established (GAP-AEBS-010-009; no re-capture planned, owner decision 2026-10-09); not a certification-grade freshness argument.";
  }

  part degradedRenderingEvidence : RetainedVisualizationEvidence {
    doc /*
     * EVID-AEBS-S2-006. Degraded-state rendering evidence from the state
     * campaign: stale, unavailable, and invalid dispositions rendered with
     * live geometry cleared and the health chip identifying the degraded
     * condition. The frame source was the PF-004 deterministic publisher,
     * NOT live Autoware 009B data; this evidence is fixture-path only and
     * must not be presented as live-chain evidence.
     */
    attribute :>> configurationIdentity = "AEBS-CONFIG-010-001";
    attribute :>> executionEnvironmentIdentity = "gcp-europe-west4-a de4sdv-aaos-build, sdv_ivi_cf guest, state-campaign generation";
    attribute :>> contractIdentity = "PF-004 deterministic publisher injection contract";
    attribute :>> rawObservationArtifact = "implementation/aebs-aaos-sdv-visualization-bench/evidence/010/state-campaign/stale.png";
    attribute :>> independentObserverIdentity = "per-state UI hierarchy dumps (state-campaign/*.xml)";
    attribute :>> disposition = VisualizationEvidenceDisposition::observedUnidentifiedBuild;
    attribute :>> claimBoundary = "Fixture-path rendering evidence only, on a build whose identity the state campaign does not record (GAP-AEBS-010-009; no re-capture planned, owner decision 2026-10-09); not live Autoware degradation evidence.";
  }

  part restorationEvidencePlanned : PlannedExecutionEnvironmentEvidence {
    doc /*
     * EVID-AEBS-S2-007 (planned). Restoration behavior after a failure
     * disposition was not exercised in any retained INC-AEBS-010 campaign.
     * This record is explicitly planned evidence: it supports no observed
     * claim and is bound to the restoration gap below. Planned scope: the
     * restored indication after the selected consecutive-valid-frame
     * criterion, without application restart.
     */
  }

  /* ──────────────────────────────────────────
   * Verification cases
   * ────────────────────────────────────────── */

  /* Each objective verifies the design-input requirements whose success
   * criteria the case checks; each verified requirement states successCriteria
   * or is listed in GAP-AEBS-010-010. Every case collects a
   * RetainedVisualizationEvidence record and is bound by its evidence-integrity
   * obligation (formerly AC-AEBS-S2-008). A requirement's subject is the
   * visualization test system, so each verified requirement binds it to the
   * bench's system2Instrument, the visualization test system as realized in
   * the configured test article, instead of the whole bench. A verify is a
   * planned verification objective, not a verdict: the verdict stays the
   * case's evidence-bound return value. */

  verification def VisualizationChainCorrelationVerification {
    subject verifiedBench : VisualizationVerificationBench;
    objective chainCorrelationObjective {
      verify reqEvidenceCorrelation { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationLifecycleArcVerification {
    subject verifiedBench : VisualizationVerificationBench;
    objective lifecycleArcObjective {
      verify reqRealAAOSRendering { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationReadOnlyBoundaryVerification {
    subject verifiedBench : VisualizationVerificationBench;
    objective readOnlyBoundaryObjective {
      verify reqNonInterference { subject visualizationTestSystem = verifiedBench.system2Instrument; }
      verify reqReadOnlyBoundaryStatement { subject visualizationTestSystem = verifiedBench.system2Instrument; }
    }
    action collectData {
      @VerificationMethod{ kind = (inspect, test); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationProvenanceSeparationVerification {
    subject verifiedBench : VisualizationVerificationBench;
    objective provenanceSeparationObjective {
      verify reqNoNativeImpersonation { subject visualizationTestSystem = verifiedBench.system2Instrument; }
      verify reqObstacleGeometryFromFilteredCloud { subject visualizationTestSystem = verifiedBench.system2Instrument; }
      verify reqNoDisplayDerivedDecisionMetric { subject visualizationTestSystem = verifiedBench.system2Instrument; }
      verify reqDecisionDistanceExclusionStatement { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationFailClosedStalenessVerification {
    doc /*
     * Its retained take exercised the expiry of obstacle geometry when the
     * filtered obstacle-cloud source stops while frames continue
     * (REQ-AEBS-S2-019); the frame-timeout trigger of REQ-AEBS-S2-006 was not
     * exercised by that take.
     */
    subject verifiedBench : VisualizationVerificationBench;
    objective failClosedStalenessObjective {
      verify reqObstacleGeometryExpiry { subject visualizationTestSystem = verifiedBench.system2Instrument; }
      verify reqNoFreshDataSubstitution { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationDegradedRenderingVerification {
    doc /*
     * Fixture-path verification case. Its subject scenario uses the PF-004
     * deterministic publisher; any verdict from it is bounded to that path
     * and does not transfer to the live Autoware chain. The same campaign
     * renders the stale and invalid degraded dispositions the same way; that
     * observation is not a success criterion of REQ-AEBS-S2-006 or
     * REQ-AEBS-S2-008 (split from the retired AC-AEBS-S2-006).
     */
    subject verifiedBench : VisualizationVerificationBench;
    objective degradedRenderingObjective {
      verify reqAvailabilityDisposition { subject visualizationTestSystem = verifiedBench.system2Instrument; }
      verify reqNonColorStateCue { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationRestorationVerification {
    doc /*
     * Planned verification case. No retained campaign exercised restoration;
     * the case exists to bind the success criteria of REQ-AEBS-S2-009 and the
     * gap, and its verdict
     * remains inconclusive until evidence is retained by a later campaign.
     */
    subject verifiedBench : VisualizationVerificationBench;
    objective restorationObjective {
      verify reqRestorationBehavior { subject visualizationTestSystem = verifiedBench.system2Instrument; }
    }
    action collectData {
      @VerificationMethod{ kind = test; }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  /* Planned verification cases for the requirements that no retained
   * campaign verifies. They are planning only: not executed, no evidence
   * record bound, no argument supporting the claim. Their requirements state
   * no success criteria yet (GAP-AEBS-010-010), so each verdict stays
   * inconclusive at least until those criteria exist and a later campaign
   * retains evidence that meets them and the evidence-integrity obligation. */

  verification def VisualizationLiveSourceFidelityVerification {
    doc /*
     * Planned verification case, not executed. On the live bench chain it
     * checks that the visualization test system consumes the pinned native
     * Autoware AEB output (RSS threshold data and the native intervention
     * diagnostic) and the DE4SDV AEBS coordinator's warning request, braking
     * request, and intervention lifecycle state, and that each displayed
     * value or state keeps the source identity, timestamp, units, coordinate
     * frame, freshness, validity, and bounded cardinality of its source frame.
     */
    subject verifiedBench : VisualizationVerificationBench;
    objective liveSourceFidelityObjective {
      verify reqSourceFidelity { subject visualizationTestSystem = verifiedBench.system2Instrument; }
      verify reqNativeParticipation { subject visualizationTestSystem = verifiedBench.system2Instrument; }
      verify reqDe4sdvParticipation { subject visualizationTestSystem = verifiedBench.system2Instrument; }
    }
    action collectData {
      @VerificationMethod{ kind = test; }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationStaleAndInvalidFrameVerification {
    doc /*
     * Planned fixture-path verification case, not executed. Scope: synthetic
     * degraded inputs only. Deterministic frame injection, not live Autoware
     * output, withholds valid frames beyond the stale timeout bound as
     * AO-AEBS-010-005, then injects unsupported-schema, malformed,
     * non-finite, out-of-range, stale-timestamp, and non-monotonic frames. It
     * checks the explicit stale disposition with threat geometry suppressed,
     * and the rejection of each invalid frame without displaying its payload
     * values. The case does not verify the live chain: any verdict is bounded
     * to the fixture path, and degraded conditions of the live Autoware chain
     * stay unobserved (GAP-AEBS-010-007). The owner accepted this
     * fixture-path scope on 2026-10-09.
     */
    subject verifiedBench : VisualizationVerificationBench;
    objective staleAndInvalidFrameObjective {
      verify reqFailClosedFreshness { subject visualizationTestSystem = verifiedBench.system2Instrument; }
      verify reqInvalidRejection { subject visualizationTestSystem = verifiedBench.system2Instrument; }
    }
    action collectData {
      @VerificationMethod{ kind = test; }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  verification def VisualizationRenderingEnvironmentVerification {
    doc /*
     * Planned verification case, not executed. In one rendered session it
     * checks that the retained session records hold observations of the AAOS
     * SDV guest package manager, system server, display composition, vehicle
     * service, and SDV gateway from that same session (test). It inspects the
     * realization and the session to confirm that the AEBS rendering surface
     * is the native guest application, not a host-side browser page (inspect).
     */
    subject verifiedBench : VisualizationVerificationBench;
    objective renderingEnvironmentObjective {
      verify reqAaosEnvironmentObservation { subject visualizationTestSystem = verifiedBench.system2Instrument; }
      verify reqNoHostBrowserSurface { subject visualizationTestSystem = verifiedBench.system2Instrument; }
    }
    action collectData {
      @VerificationMethod{ kind = (test, inspect); }
      out item retainedEvidence : RetainedVisualizationEvidence;
    }
    action processData {
      @VerificationMethod{ kind = analyze; }
      in scenarioIdentity : VisualizationScenario = verifiedBench.scenario;
      in item retainedEvidence : RetainedVisualizationEvidence = collectData.retainedEvidence;
      out item replayedEvaluation : ReplayedVisualizationEvaluation;
    }
    action evaluateData {
      @VerificationMethod{ kind = analyze; }
      in item replayedEvaluation : ReplayedVisualizationEvaluation = processData.replayedEvaluation;
      out verdict : VerdictKind = MapVisualizationOutcomeToVerdict(replayedEvaluation.outcome);
    }
    return verdict : VerdictKind = evaluateData.verdict;
  }

  doc /* VC-AEBS-S2-001 verification case usage. */
  verification chainCorrelationVerification : VisualizationChainCorrelationVerification {
    @VerificationMethod{ kind = (test, inspect, analyze); }
    subject verifiedBench :> liveChainCorrelationBench;
  }

  doc /* VC-AEBS-S2-002 verification case usage. */
  verification lifecycleArcVerification : VisualizationLifecycleArcVerification {
    doc /* VC-AEBS-S2-002: its retained evidence, EVID-AEBS-S2-002, rests on a verified-stop reading of RELEASED that the take's own frame log contradicts. Contradicted by the retained data; by owner decision of 2026-10-09 no re-capture is planned, so the case stays inconclusive (GAP-AEBS-010-009, CCM-AEBS-S2-05). */
    @VerificationMethod{ kind = (test, inspect, analyze); }
    subject verifiedBench :> lifecycleArcBench;
  }

  doc /* VC-AEBS-S2-003 verification case usage. */
  verification readOnlyBoundaryVerification : VisualizationReadOnlyBoundaryVerification {
    doc /* VC-AEBS-S2-003: the success criteria of REQ-AEBS-S2-015 were formalized after the retained take; they are not assessed against EVID-AEBS-S2-003, and the case verdict does not cover them. */
    @VerificationMethod{ kind = (test, inspect, analyze); }
    subject verifiedBench :> readOnlyBoundaryBench;
  }

  doc /* VC-AEBS-S2-004 verification case usage. */
  verification provenanceSeparationVerification : VisualizationProvenanceSeparationVerification {
    doc /* VC-AEBS-S2-004: the success criteria of REQ-AEBS-S2-016, -017 and -018 were formalized after the retained take; they are not assessed against EVID-AEBS-S2-004, and the case verdict does not cover them. */
    @VerificationMethod{ kind = (test, inspect, analyze); }
    subject verifiedBench :> provenanceSeparationBench;
  }

  doc /* VC-AEBS-S2-005 verification case usage. */
  verification failClosedStalenessVerification : VisualizationFailClosedStalenessVerification {
    doc /* VC-AEBS-S2-005: the retained take does not establish the cloud-silence trigger that the success criteria of REQ-AEBS-S2-019 name (GAP-AEBS-010-009, CCM-AEBS-S2-05); a scoped observation on an unidentified build; no re-capture is planned (owner decision 2026-10-09). The success criteria of REQ-AEBS-S2-020 were formalized after the retained take; they are not assessed against EVID-AEBS-S2-005, and the case verdict does not cover them. */
    @VerificationMethod{ kind = (test, inspect, analyze); }
    subject verifiedBench :> failClosedStalenessBench;
  }

  doc /* VC-AEBS-S2-006 verification case usage. */
  verification degradedRenderingVerification : VisualizationDegradedRenderingVerification {
    doc /* VC-AEBS-S2-006: the success criteria of REQ-AEBS-S2-021 were formalized after the retained take; they are not assessed against EVID-AEBS-S2-006, and the case verdict does not cover them. */
    @VerificationMethod{ kind = (test, inspect, analyze); }
    subject verifiedBench :> degradedStateRenderingBench;
  }

  doc /* VC-AEBS-S2-007 verification case usage. */
  verification restorationVerification : VisualizationRestorationVerification {
    @VerificationMethod{ kind = (test, analyze); }
    subject verifiedBench :> restorationBehaviorBench;
  }

  doc /* VC-AEBS-S2-008 verification case usage. */
  verification liveSourceFidelityVerification : VisualizationLiveSourceFidelityVerification {
    doc /* VC-AEBS-S2-008: planned, not executed; no evidence record is bound. */
    @VerificationMethod{ kind = (test, analyze); }
    subject verifiedBench :> liveSourceFidelityBench;
  }

  doc /* VC-AEBS-S2-009 verification case usage. */
  verification staleAndInvalidFrameVerification : VisualizationStaleAndInvalidFrameVerification {
    doc /* VC-AEBS-S2-009: planned fixture-path case on synthetic degraded inputs, not executed; it does not verify the live chain, and no evidence record is bound. */
    @VerificationMethod{ kind = (test, analyze); }
    subject verifiedBench :> staleAndInvalidFramesBench;
  }

  doc /* VC-AEBS-S2-010 verification case usage. */
  verification renderingEnvironmentVerification : VisualizationRenderingEnvironmentVerification {
    doc /* VC-AEBS-S2-010: planned, not executed; no evidence record is bound. */
    @VerificationMethod{ kind = (test, inspect, analyze); }
    subject verifiedBench :> renderingEnvironmentBench;
  }

  part visualizationVerificationSystem {
    perform chainCorrelationVerification;
    perform lifecycleArcVerification;
    perform readOnlyBoundaryVerification;
    perform provenanceSeparationVerification;
    perform failClosedStalenessVerification;
    perform degradedRenderingVerification;
    perform restorationVerification;
    perform liveSourceFidelityVerification;
    perform staleAndInvalidFrameVerification;
    perform renderingEnvironmentVerification;
  }

  /* Cross-increment traceability to the configured test article. The
   * configuration role (AEBS-CONFIG-010-001, testArticle) and the subject
   * role (the visualization test system as realized in that article) are
   * traced separately; no allocation relates them. */
  dependency verificationTestArticleTrace
    from visualizationVerificationSystem
    to testArticle;
  dependency verificationInstrumentTrace
    from visualizationVerificationSystem
    to testArticle::visualizationChain::instrument;
  dependency chainEvidenceToTestArticleChainTrace
    from liveChainEvidence
    to testArticle::visualizationChain;
  dependency lifecycleEvidenceToDisplayAppTrace
    from lifecycleArcEvidence
    to testArticle::visualizationChain::instrument::iviGuest::displayApp;
  dependency provenanceEvidenceToSourceProvenanceTrace
    from provenanceSeparationEvidence
    to coordinatorStateProvenance;

  /* ──────────────────────────────────────────
   * Claim-argument-evidence layer (INC-AEBS-010 Phase 10)
   * ────────────────────────────────────────── */

  /* Assurance artifacts, not requirements: they consume the verification
   * results above and do not derive from needs. */
  requirement def VisualizationClaim :> AssuranceClaim;

  requirement def VisualizationArgument :> AssuranceArgument;

  requirement def VisualizationCounterClaim :> AssuranceCounterClaim;

  requirement visualizationInstrumentationClaim : VisualizationClaim {
    doc /*
     * CLM-AEBS-S2-001: for AEBS-CONFIG-010-001 on the retained campaign
     * environment, the read-only visualization instrumentation observed the
     * live pinned-Autoware chain into the AAOS guest, rendered the complete
     * reducer-driven four-state arc in one uninterrupted take, preserved the
     * display-derived versus native decision-semantics separation in every
     * public frame, suppressed expired display-derived geometry fail-closed,
     * and rendered degraded dispositions under deterministic fixture
     * injection. The scenario-safety outcome remains deferred_not_proven:
     * this claim is about the instrumentation, never about AEBS safety.
     */
    subject claimSubject : VisualizationVerificationBench;
    require constraint {
      doc /*
       * The claim requires retained EVID-AEBS-S2-001 through EVID-AEBS-S2-006
       * evidence bound to the configured test article, exact wire contract,
       * execution environment, and independent observer identities. It
       * excludes restoration behavior, live degradation beyond the retained
       * take, inter-VM transport without the bounded bench route, signed-
       * policy enforcement, post-release re-approach, safety, certification,
       * homologation, and production-readiness claims.
       */
    }
  }

  requirement chainCorrelationArgument : VisualizationArgument {
    doc /* AGT-AEBS-S2-01: argues the success criteria of REQ-AEBS-S2-011 (formerly AC-AEBS-S2-001; source-to-screen correlation with zero gaps) within the claim boundary. */
    subject bench : VisualizationVerificationBench;
  }

  requirement lifecycleArcArgument : VisualizationArgument {
    doc /* AGT-AEBS-S2-02: argues the success criteria of REQ-AEBS-S2-010 (formerly AC-AEBS-S2-002; one-take four-state arc with a verified zero-speed stop at release) within the claim boundary. Its evidence is contradicted by the retained data on post-release motion (CCM-AEBS-S2-05); no re-capture is planned (owner decision 2026-10-09). */
    subject bench : VisualizationVerificationBench;
  }

  requirement readOnlyBoundaryArgument : VisualizationArgument {
    doc /* AGT-AEBS-S2-03: argues the success criteria of REQ-AEBS-S2-005 (formerly AC-AEBS-S2-003; read-only, no vehicle command) within the claim boundary. */
    subject bench : VisualizationVerificationBench;
  }

  requirement provenanceSeparationArgument : VisualizationArgument {
    doc /* AGT-AEBS-S2-04: argues the success criteria of REQ-AEBS-S2-014 (formerly AC-AEBS-S2-004; display-derived versus native separation) within the claim boundary. */
    subject bench : VisualizationVerificationBench;
  }

  requirement failClosedStalenessArgument : VisualizationArgument {
    doc /* AGT-AEBS-S2-05: argues the success criteria of REQ-AEBS-S2-019 (formerly AC-AEBS-S2-005; fail-closed suppression of expired geometry) within the claim boundary. The retained take does not establish the cloud-silence trigger (CCM-AEBS-S2-05). */
    subject bench : VisualizationVerificationBench;
  }

  requirement degradedRenderingArgument : VisualizationArgument {
    doc /* AGT-AEBS-S2-06: argues the success criteria of REQ-AEBS-S2-007 (formerly AC-AEBS-S2-006) bounded to the fixture path; live-chain degradation is not argued by this branch. */
    subject bench : VisualizationVerificationBench;
  }

  requirement counterClaimRestoration : VisualizationCounterClaim {
    doc /* CCM-AEBS-S2-01: bounds the claim for restoration behavior (the success criteria of REQ-AEBS-S2-009, formerly AC-AEBS-S2-007); no retained campaign exercised it. */
    subject bench : VisualizationVerificationBench;
  }

  requirement counterClaimLiveDegradation : VisualizationCounterClaim {
    doc /* CCM-AEBS-S2-02: bounds the claim for live degraded dispositions (stale/unavailable/invalid) from real Autoware source conditions; retained degraded-state evidence is fixture-path only. */
    subject bench : VisualizationVerificationBench;
  }

  requirement counterClaimProductionBoundaries : VisualizationCounterClaim {
    doc /* CCM-AEBS-S2-03: bounds the claim against inter-VM transport without the bounded adb-reverse bench route, signed-policy enforcement, production HMI, and any safety or certification reading. */
    subject bench : VisualizationVerificationBench;
  }

  requirement counterClaimUnidentifiedBuild : VisualizationCounterClaim {
    doc /* CCM-AEBS-S2-04: bounds the claim to observations on builds that are not exactly identified (GAP-AEBS-010-009); it verifies nothing on the configured test article. By owner decision of 2026-10-09 no re-capture is planned: the retained take stands as a scoped observation (demonstrated on a build derived from 4d8dc1b, not verification of an identified configuration), and no verification claim is made. */
    subject bench : VisualizationVerificationBench;
  }

  requirement counterClaimRetainedRecordContradicted : VisualizationCounterClaim {
    doc /* CCM-AEBS-S2-05: bounds the claim where the retained records are not borne out by their own data (GAP-AEBS-010-009). The lifecycle-arc branch (AGT-AEBS-S2-02, VC-AEBS-S2-002) rests on a verified-stop reading of RELEASED that the take's frame log contradicts. The fail-closed branch (AGT-AEBS-S2-05, VC-AEBS-S2-005) cannot establish its cloud-silence trigger. The records also named an execution environment the take did not use. No re-capture is planned (owner decision 2026-10-09), and no verification claim is made. */
    subject bench : VisualizationVerificationBench;
  }

  dependency claimSupportedByChainArgument
    from chainCorrelationArgument to visualizationInstrumentationClaim;
  dependency claimSupportedByLifecycleArgument
    from lifecycleArcArgument to visualizationInstrumentationClaim;
  dependency claimSupportedByReadOnlyArgument
    from readOnlyBoundaryArgument to visualizationInstrumentationClaim;
  dependency claimSupportedByProvenanceArgument
    from provenanceSeparationArgument to visualizationInstrumentationClaim;
  dependency claimSupportedByStalenessArgument
    from failClosedStalenessArgument to visualizationInstrumentationClaim;
  dependency claimSupportedByDegradedArgument
    from degradedRenderingArgument to visualizationInstrumentationClaim;

  dependency chainVerificationReinforcesArgument
    from chainCorrelationVerification to chainCorrelationArgument;
  dependency lifecycleVerificationReinforcesArgument
    from lifecycleArcVerification to lifecycleArcArgument;
  dependency readOnlyVerificationReinforcesArgument
    from readOnlyBoundaryVerification to readOnlyBoundaryArgument;
  dependency provenanceVerificationReinforcesArgument
    from provenanceSeparationVerification to provenanceSeparationArgument;
  dependency stalenessVerificationReinforcesArgument
    from failClosedStalenessVerification to failClosedStalenessArgument;
  dependency degradedVerificationReinforcesArgument
    from degradedRenderingVerification to degradedRenderingArgument;

  dependency chainEvidenceReinforcesChainArgument
    from liveChainEvidence to chainCorrelationArgument;
  dependency lifecycleEvidenceReinforcesLifecycleArgument
    from lifecycleArcEvidence to lifecycleArcArgument;
  dependency readOnlyEvidenceReinforcesReadOnlyArgument
    from readOnlyBoundaryEvidence to readOnlyBoundaryArgument;
  dependency provenanceEvidenceReinforcesProvenanceArgument
    from provenanceSeparationEvidence to provenanceSeparationArgument;
  dependency stalenessEvidenceReinforcesStalenessArgument
    from failClosedStalenessEvidence to failClosedStalenessArgument;
  dependency degradedEvidenceReinforcesDegradedArgument
    from degradedRenderingEvidence to degradedRenderingArgument;

  dependency chainEvidenceTraceToClaim
    from liveChainEvidence to visualizationInstrumentationClaim;
  dependency lifecycleEvidenceTraceToClaim
    from lifecycleArcEvidence to visualizationInstrumentationClaim;
  dependency readOnlyEvidenceTraceToClaim
    from readOnlyBoundaryEvidence to visualizationInstrumentationClaim;
  dependency provenanceEvidenceTraceToClaim
    from provenanceSeparationEvidence to visualizationInstrumentationClaim;
  dependency stalenessEvidenceTraceToClaim
    from failClosedStalenessEvidence to visualizationInstrumentationClaim;
  dependency degradedEvidenceTraceToClaim
    from degradedRenderingEvidence to visualizationInstrumentationClaim;

  dependency counterClaimRestorationCountersClaim
    from counterClaimRestoration to visualizationInstrumentationClaim;
  dependency counterClaimLiveDegradationCountersClaim
    from counterClaimLiveDegradation to visualizationInstrumentationClaim;
  dependency counterClaimProductionCountersClaim
    from counterClaimProductionBoundaries to visualizationInstrumentationClaim;
  dependency counterClaimUnidentifiedBuildCountersClaim
    from counterClaimUnidentifiedBuild to visualizationInstrumentationClaim;
  dependency counterClaimRetainedRecordCountersClaim
    from counterClaimRetainedRecordContradicted to visualizationInstrumentationClaim;

  /* ──────────────────────────────────────────
   * Gaps (deferred scope owned by this slice's successors)
   * ────────────────────────────────────────── */

  part gap010RestorationUnexercised : IncrementGap {
    doc /*
     * GAP-AEBS-010-006: Restoration after a failure disposition
     * (REQ-AEBS-S2-009, success criteria formerly AC-AEBS-S2-007) was not
     * exercised in any retained INC-AEBS-010
     * campaign; the deterministic PF-004 publisher can exercise it without
     * live bench time. Owner: successor increment in this chain.
     */
  }
  part gap010LiveDegradationUnproven : IncrementGap {
    doc /*
     * GAP-AEBS-010-007: Degraded dispositions from real Autoware source
     * conditions (stale/unavailable/invalid on the live chain) are not
     * observed in retained evidence; the retained degraded-state campaign is
     * fixture-path only. REQ-AEBS-S2-006 (no-valid-frame timeout) and
     * REQ-AEBS-S2-008 (invalid-frame rejection) have only the planned
     * fixture-path case VC-AEBS-S2-009, which is not executed: no retained
     * evidence verifies them, and a fixture-path verdict would not transfer
     * to the live chain. Owner: successor increment in this chain.
     */
  }
  part gap010InterVmRouteDeferred : DeferredProductLineScope {
    doc /*
     * GAP-AEBS-010-008: The retained route is the bounded bench transport
     * (TCP :4721 + adb reverse). An inter-VM route without the adb-reverse
     * shortcut and a signed-policy enforcement path (SELinux stays permissive
     * on the bench guest) remain deferred; production must enforce policy.
     * Owner: successor increment in this chain.
     */
  }
  part gapRetainedEvidenceIntegrity : IncrementGap {
    doc /*
     * GAP-AEBS-010-009: the retained evidence EVID-AEBS-S2-001..006 cannot
     * serve as verification of the configured test article
     * AEBS-CONFIG-010-001, for three reasons.
     *
     * Build identity. The v21 take (final-hmi-v21-corrected), the source of
     * EVID-AEBS-S2-001..005, was captured from HEAD 4d8dc1b plus 17
     * uncommitted files. It is identified only by sha256 prefixes of six
     * corrected sources (revision-checksums.md). The fixture-path state
     * campaign (EVID-AEBS-S2-006) records no build identity at all.
     *
     * Contradicted record. The take's segment record states that the ego
     * does not re-accelerate after release. Its own frame log shows release
     * at seq 23034 at 0.0 m/s, then the ego speed rising from seq 23036 and
     * holding 6.876 m/s from seq 23091 to the end of the log, with
     * braking=true on all 947 RELEASED frames. The verified-stop reading of
     * RELEASED (EVID-AEBS-S2-002, VC-AEBS-S2-002) is contradicted by the
     * retained data. The last geometry clearing (seq 23091) coincides with
     * the ego driving on, so the cloud-silence reading of EVID-AEBS-S2-005
     * is not established either.
     *
     * Pedigree error. The evidence records named a second VM,
     * de4sdv-ros2-autoware, as part of the execution environment. This take
     * did not use it: its route is adb reverse (segment.yaml), and its
     * observer ran on de4sdv-aaos-build (observer.log). The string came from
     * the earlier VM-B campaigns (evidence/010/vmb-live). EVID-AEBS-S2-001,
     * -002, -004 and -005 now carry the corrected string.
     *
     * The retained artifacts stay as captured. By owner decision of
     * 2026-10-09 no re-capture is planned: the retained take stands as a
     * scoped observation (demonstrated on a build derived from 4d8dc1b, not
     * verification of an identified configuration), and no verification
     * claim is made. The gap stays open as an accepted limitation; any later
     * verification belongs to a successor increment in this chain.
     */
  }
  part gapRequirementSuccessCriteriaMissing : IncrementGap {
    doc /*
     * GAP-AEBS-010-010: REQ-AEBS-S2-002, REQ-AEBS-S2-003, REQ-AEBS-S2-004,
     * REQ-AEBS-S2-006, REQ-AEBS-S2-008, REQ-AEBS-S2-012 and REQ-AEBS-S2-013
     * state no successCriteria. Their planned cases VC-AEBS-S2-008..010 have
     * no requirement-specific success criterion to check. The criteria are to
     * be defined before these requirements are baselined. Owner: successor
     * increment in this chain.
     */
  }

  dependency counterClaimRestorationGapTrace
    from counterClaimRestoration to gap010RestorationUnexercised;
  dependency counterClaimLiveDegradationGapTrace
    from counterClaimLiveDegradation to gap010LiveDegradationUnproven;
  dependency counterClaimProductionGapTrace
    from counterClaimProductionBoundaries to gap010InterVmRouteDeferred;
  dependency plannedRestorationEvidenceGapTrace
    from restorationEvidencePlanned to gap010RestorationUnexercised;
  dependency counterClaimUnidentifiedBuildGapTrace
    from counterClaimUnidentifiedBuild to gapRetainedEvidenceIntegrity;
  dependency counterClaimRetainedRecordGapTrace
    from counterClaimRetainedRecordContradicted to gapRetainedEvidenceIntegrity;
  dependency liveChainEvidenceIntegrityGapTrace
    from liveChainEvidence to gapRetainedEvidenceIntegrity;
  dependency lifecycleArcEvidenceIntegrityGapTrace
    from lifecycleArcEvidence to gapRetainedEvidenceIntegrity;
  dependency readOnlyBoundaryEvidenceIntegrityGapTrace
    from readOnlyBoundaryEvidence to gapRetainedEvidenceIntegrity;
  dependency provenanceSeparationEvidenceIntegrityGapTrace
    from provenanceSeparationEvidence to gapRetainedEvidenceIntegrity;
  dependency failClosedStalenessEvidenceIntegrityGapTrace
    from failClosedStalenessEvidence to gapRetainedEvidenceIntegrity;
  dependency degradedRenderingEvidenceIntegrityGapTrace
    from degradedRenderingEvidence to gapRetainedEvidenceIntegrity;

  /* Safety non-claim anchor: the scenario-safety outcome stays deferred. */
  part scenarioSafetyDeferred : DeferredProductLineScope {
    doc /*
     * The visualization observes AEBS behavior; it contributes no braking
     * authority, hazard control, or safety argument. The scenario-safety
     * outcome remains deferred_not_proven by design of this instrumentation.
     */
  }
  dependency readOnlyArgumentSafetyNonClaimTrace
    from readOnlyBoundaryArgument to scenarioSafetyDeferred;

  /* ──────────────────────────────────────────
   * Concern and views (ArgumentationAssurance for evidence claims)
   * ────────────────────────────────────────── */

  concern visualizationArgumentationAssuranceConcern : ArgumentationAssuranceConcern {
    doc /*
     * Systems engineers, verification engineers and open-source reviewers
     * need the evidence-based assurance claim, the counterclaims, the retained
     * evidence, and the gaps for the visualization instrumentation.
     */
    subject;
    stakeholder systemsEngineer : SystemsEngineer;
    stakeholder verificationEngineer : VerificationEngineer;
    stakeholder reviewer : OpenSourceReviewer;
  }

  view aebsVisualizationVerificationAssuranceView {
    viewpoint selectedAssuranceViewpoint : ArgumentationAssuranceViewpoint {
      frame visualizationArgumentationAssuranceConcern;
    }
    doc /*
     * Positive Phase 10 slice: the bounded instrumentation claim, its
     * supporting arguments, and the retained evidence branches.
     */
    expose visualizationInstrumentationClaim;
    expose chainCorrelationArgument;
    expose lifecycleArcArgument;
    expose readOnlyBoundaryArgument;
    expose provenanceSeparationArgument;
    expose failClosedStalenessArgument;
    expose degradedRenderingArgument;
    expose liveChainEvidence;
    expose lifecycleArcEvidence;
    expose readOnlyBoundaryEvidence;
    expose provenanceSeparationEvidence;
    expose failClosedStalenessEvidence;
    expose degradedRenderingEvidence;
    expose claimSupportedByChainArgument;
    expose claimSupportedByLifecycleArgument;
    expose claimSupportedByReadOnlyArgument;
    expose claimSupportedByProvenanceArgument;
    expose claimSupportedByStalenessArgument;
    expose claimSupportedByDegradedArgument;
    attribute maxCompartmentEntries = 0;
    attribute showAnnotationRows = false;
    render asTreeDiagram;
  }

  view aebsVisualizationOpenCounterclaimAssuranceView {
    viewpoint selectedOpenCounterclaimViewpoint : ArgumentationAssuranceViewpoint {
      frame visualizationArgumentationAssuranceConcern;
    }
    doc /*
     * Challenge slice: unresolved counterclaims and gaps that prevent
     * broader restoration, live-degradation, inter-VM, and safety assurance,
     * and verification on an exactly identified build with records its data
     * bears out.
     */
    expose visualizationInstrumentationClaim;
    expose counterClaimRestoration;
    expose counterClaimLiveDegradation;
    expose counterClaimProductionBoundaries;
    expose counterClaimUnidentifiedBuild;
    expose counterClaimRetainedRecordContradicted;
    expose gap010RestorationUnexercised;
    expose gap010LiveDegradationUnproven;
    expose gap010InterVmRouteDeferred;
    expose gapRetainedEvidenceIntegrity;
    expose counterClaimRestorationGapTrace;
    expose counterClaimLiveDegradationGapTrace;
    expose counterClaimProductionGapTrace;
    expose counterClaimUnidentifiedBuildGapTrace;
    expose counterClaimRetainedRecordGapTrace;
    expose restorationEvidencePlanned;
    expose scenarioSafetyDeferred;
    attribute maxCompartmentEntries = 0;
    attribute showAnnotationRows = false;
    render asTreeDiagram;
  }
}
