/*
 * GfSE SAF viewpoint and concern definitions used by DE4SDV.
 *
 * Source: https://saf.gfse.org/userdoc/viewpoints.html
 * Repository: https://github.com/GfSE/SAF-Specification
 * License: Apache-2.0
 *
 * This package is a source-backed reference catalogue, not a vendored copy.
 * DE4SDV-specific method-governance viewpoints remain in
 * DE4SDV_MethodViewpoints, not here.
 */

package SAF_Viewpoints {
  private import Views::*;

  // ─── SAF domains ───
  // The rows of the SAF grid. Each concern and viewpoint definition of this
  // catalogue specializes the abstract definition of its domain, so the domain is
  // a fact of the model that a check reads by identity, not a comment.

  abstract concern def ArchitectureManagementDomainConcern {
    doc /*
     * A concern of the SAF Architecture Management Domain: content that spans
     * the architecture, such as terms, applicable standards, the assurance
     * argument and the traceability between the architecture's artifacts.
     */
  }

  abstract viewpoint def ArchitectureManagementDomainViewpoint {
    doc /* A viewpoint of the SAF Architecture Management Domain. */
  }

  abstract concern def OperationalDomainConcern {
    doc /*
     * A concern of the SAF Operational Domain: the concept phase, that is the
     * mission, the stakeholders and their needs, and the operational context,
     * capabilities, stories and processes of the organization or operational
     * entity, before a system solution is chosen.
     */
  }

  abstract viewpoint def OperationalDomainViewpoint {
    doc /* A viewpoint of the SAF Operational Domain. */
  }

  abstract concern def ConceptualDomainConcern {
    doc /*
     * A concern of the SAF Conceptual Domain: the functional and logical
     * architecture of the system, that is its behavior at the system boundary,
     * its functions, logical elements, exchanges, interfaces and requirements,
     * and its security analysis. A question about a concrete platform, product
     * or component that realizes the system is a Physical Domain concern.
     */
  }

  abstract viewpoint def ConceptualDomainViewpoint {
    doc /* A viewpoint of the SAF Conceptual Domain. */
  }

  abstract concern def PhysicalDomainConcern {
    doc /*
     * A concern of the SAF Physical Domain: the design definition of the
     * system, that is its physical and software elements, including reused and
     * off-the-shelf products and platforms, their physical interfaces and
     * exchanges, and the mapping of functional and logical elements to them.
     */
  }

  abstract viewpoint def PhysicalDomainViewpoint {
    doc /* A viewpoint of the SAF Physical Domain. */
  }

  abstract concern def SAFDevelopmentDomainConcern {
    doc /*
     * A concern of the SAF Development Domain: the development, maintenance
     * and extension of the framework itself.
     */
  }

  abstract viewpoint def SAFDevelopmentDomainViewpoint {
    doc /* A viewpoint of the SAF Development Domain. */
  }

  // ─── Architecture Management Domain ───

  concern def CommonTermsConcern :> ArchitectureManagementDomainConcern {
    require constraint {
      doc /*
       * Reviewers need terms introduced by an increment to be defined
       * in a glossary or terminology section.
       */
    }
  }

  viewpoint def CommonTermsDefinitionViewpoint :> ArchitectureManagementDomainViewpoint {
    doc /*
     * SAF Architecture Management Domain: Common Terms Definition Viewpoint.
     * Aspect: Taxonomy & Structure
     * Source: https://saf.gfse.org/userdoc/viewpoints.html
     */
    require constraint {
      doc /*
       * A common terms view shall define terms introduced by the
       * increment in a glossary or terminology section.
       */
    }
  }

  concern def CommonStandardsConcern :> ArchitectureManagementDomainConcern {
    require constraint {
      doc /*
       * Reviewers need standards and regulations used as constraints
       * or references to be registered with source attribution.
       */
    }
  }

  viewpoint def CommonStandardsDefinitionViewpoint :> ArchitectureManagementDomainViewpoint {
    doc /*
     * SAF Architecture Management Domain: Common Standards Definition Viewpoint.
     * Aspect: Taxonomy & Structure
     * Source: https://saf.gfse.org/userdoc/viewpoints.html
     */
    require constraint {
      doc /*
       * A common standards view shall register standards, regulations,
       * and external references used as constraints with source
       * attribution and scope notes.
       */
    }
  }

  concern def EATraceabilityConcern :> ArchitectureManagementDomainConcern {
    require constraint {
      doc /*
       * Reviewers need these questions answered for the increment: Which
       * element of a system model is derived from an element of the
       * enterprise architecture model? Which element of a system model is
       * influenced by an element of the enterprise architecture model? Which
       * element of a system model represents the same entity as an other
       * element of the enterprise architecture model?
       */
    }
  }

  viewpoint def EATraceabilityViewpoint :> ArchitectureManagementDomainViewpoint {
    doc /*
     * SAF Architecture Management Domain: EA Traceability Viewpoint.
     * Aspect: Traceability & Mapping
     * Source: https://saf.gfse.org/userdoc/viewpoints.html
     */
    require constraint {
      doc /*
       * An EA traceability view shall map the system model to its enterprise
       * architecture model, showing which system model element represents the
       * same entity as, is derived from, or is influenced by which enterprise
       * architecture model element.
       */
    }
  }


  // ─── Operational Domain ───

  concern def StakeholderIdentificationConcern :> OperationalDomainConcern {
    require constraint {
      doc /*
       * Reviewers need roles affected by the increment to be
       * identified with their concerns.
       */
    }
  }

  viewpoint def StakeholderIdentificationViewpoint :> OperationalDomainViewpoint {
    doc /*
     * SAF Operational Domain: Stakeholder Identification Viewpoint.
     * Aspect: Taxonomy & Structure
     * Source: https://saf.gfse.org/userdoc/viewpoints.html
     */
    require constraint {
      doc /*
       * A stakeholder identification view shall identify roles
       * affected by the increment and their concerns.
       */
    }
  }

  concern def OperationalContextConcern :> OperationalDomainConcern {
    require constraint {
      doc /*
       * Reviewers need to see the operational actors, context boundary,
       * and operational story for the feature increment.
       */
    }
  }

  viewpoint def OperationalContextDefinitionViewpoint :> OperationalDomainViewpoint {
    doc /*
     * SAF Operational Domain: Operational Context Definition Viewpoint.
     * Aspect: Context & Exchange
     * Source: https://saf.gfse.org/userdoc/viewpoints.html
     */
    require constraint {
      doc /*
       * An operational context view shall show external actors, context
       * boundary, use case/actor framing, and operational behavior
       * (actions, items, flows, sequencing) for the increment.
       */
    }
  }

  concern def OperationalStoryConcern :> OperationalDomainConcern {
    require constraint {
      doc /*
       * Reviewers need the operational scenario told in stakeholder
       * language to validate fitness-for-use intent.
       */
    }
  }

  viewpoint def OperationalStoryViewpoint :> OperationalDomainViewpoint {
    doc /*
     * SAF Operational Domain: Operational Story Viewpoint.
     * Aspect: Context & Exchange
     * Source: https://saf.gfse.org/userdoc/viewpoints.html
     */
    require constraint {
      doc /*
       * An operational story view shall tell the scenario in
       * stakeholder language, connecting operational context to
       * validation intent.
       */
    }
  }

  concern def OperationalCapabilityConcern :> OperationalDomainConcern {
    require constraint {
      doc /*
       * Reviewers need the operational capability expected from the
       * product line to be described for the increment.
       */
    }
  }

  viewpoint def OperationalCapabilityDefinitionViewpoint :> OperationalDomainViewpoint {
    doc /*
     * SAF Operational Domain: Operational Capability Definition Viewpoint.
     * Aspect: Taxonomy & Structure
     * Source: https://saf.gfse.org/userdoc/viewpoints.html
     */
    require constraint {
      doc /*
       * An operational capability view shall describe the operational
       * capability expected from the product line for the increment.
       */
    }
  }

  concern def OperationalProcessConcern :> OperationalDomainConcern {
    require constraint {
      doc /*
       * Reviewers need the operational flow or lifecycle process to be
       * described for the increment.
       */
    }
  }

  viewpoint def OperationalProcessViewpoint :> OperationalDomainViewpoint {
    doc /*
     * SAF Operational Domain: Operational Process Viewpoint.
     * Aspect: Process & Behavior
     * Source: https://saf.gfse.org/userdoc/viewpoints.html
     */
    require constraint {
      doc /*
       * An operational process view shall describe the operational
       * flow or lifecycle process for the increment.
       */
    }
  }

  concern def OperationalStateConcern :> OperationalDomainConcern {
    require constraint {
      doc /*
       * Reviewers need these questions answered for the increment: What
       * operational states are defined for a system or system's operation?
       * Which operational processes are possible to be performed in an
       * operational state? Which operational states are possible results of
       * performing an operational process?
       */
    }
  }

  viewpoint def OperationalStateViewpoint :> OperationalDomainViewpoint {
    doc /*
     * SAF Operational Domain: Operational State Viewpoint.
     * Aspect: Process & Behavior
     * Source: https://saf.gfse.org/userdoc/viewpoints.html
     */
    require constraint {
      doc /*
       * An operational state view shall show the operational states defined
       * for the system or its operation, the operational processes that a
       * state allows, and the operational states a process can produce.
       */
    }
  }

  concern def StakeholderNeedsConcern :> OperationalDomainConcern {
    require constraint {
      doc /*
       * Reviewers need stakeholder needs and validation intent to be
       * visible as requirement-like usages, not generic prose.
       */
    }
  }

  viewpoint def StakeholderRequirementDefinitionViewpoint :> OperationalDomainViewpoint {
    doc /*
     * SAF Operational Domain: Stakeholder Requirement Definition Viewpoint.
     * Aspect: Requirement
     * Source: https://saf.gfse.org/userdoc/viewpoints.html
     */
    require constraint {
      doc /*
       * A stakeholder needs view shall show stakeholder needs as native
       * requirement usages, stakeholder roles, and validation intent
       * for the increment.
       */
    }
  }

  // ─── Conceptual Domain ───
  // System requirements, functional architecture, and logical architecture
  // are distinct artifact kinds in this domain. Logical architecture is the
  // technology-independent structural view. Current System* viewpoint names
  // describe the conceptual system; they do not rename the logical
  // architecture artifact or the Architecture Definition process.

  concern def SystemContextConcern :> ConceptualDomainConcern {
    require constraint {
      doc /*
       * Reviewers need these questions answered for the increment: Where and
       * what are the geographical and physical locations of the intended or
       * proposed elements of the solution? Which are the external conceptual
       * entities the system interacts with in the given context? Which are the
       * given contexts the system is embedded and utilized in? Which interface
       * partners does the system have?
       */
    }
  }

  viewpoint def SystemContextDefinitionViewpoint :> ConceptualDomainViewpoint {
    doc /*
     * SAF Conceptual Domain: System Context Definition Viewpoint.
     * Aspect: Context & Exchange
     * Source: https://saf.gfse.org/userdoc/viewpoints.html
     */
    require constraint {
      doc /*
       * A system context definition view shall show where the system of
       * interest's boundary lies, which external conceptual entities it
       * interacts with in each given context, and which interface partners it
       * has.
       */
    }
  }

  concern def SystemContextExchangeConcern :> ConceptualDomainConcern {
    require constraint {
      doc /*
       * Reviewers need these questions answered for the increment: How is the
       * system interacting with the identified external entities? Which are
       * the conceptual interfaces of the system? Which are the external
       * conceptual entities the system interacts with in the given context?
       * Which are the interface requirements imposed on the system? Which kind
       * of conceptual items (energy, material, information, etc.) are
       * exchanged between the system and external entities? Which requirements
       * apply to a conceptual interface?
       */
    }
  }

  viewpoint def SystemContextExchangeViewpoint :> ConceptualDomainViewpoint {
    doc /*
     * SAF Conceptual Domain: System Context Exchange Viewpoint.
     * Aspect: Context & Exchange
     * Source: https://saf.gfse.org/userdoc/viewpoints.html
     */
    require constraint {
      doc /*
       * A system context exchange view shall show how the system interacts
       * with each identified external entity across its conceptual interfaces,
       * which conceptual items each interface conveys, and which requirements
       * apply to it.
       */
    }
  }


  concern def SystemUseCaseConcern :> ConceptualDomainConcern {
    require constraint {
      doc /*
       * Reviewers need system use cases captured for the increment.
       */
    }
  }

  viewpoint def SystemUseCaseViewpoint :> ConceptualDomainViewpoint {
    doc /*
     * SAF Conceptual Domain: System Use Case Viewpoint.
     * Aspect: Context & Exchange
     * Source: https://saf.gfse.org/userdoc/viewpoints.html
     */
    require constraint {
      doc /*
       * A system use case view shall capture system use cases with
       * actors and objectives.
       */
    }
  }

  concern def SystemCapabilityConcern :> ConceptualDomainConcern {
    require constraint {
      doc /*
       * Reviewers need system capabilities defined for the increment.
       */
    }
  }

  viewpoint def SystemCapabilityDefinitionViewpoint :> ConceptualDomainViewpoint {
    doc /*
     * SAF Conceptual Domain: System Capability Definition Viewpoint.
     * Aspect: Taxonomy & Structure
     * Source: https://saf.gfse.org/userdoc/viewpoints.html
     */
    require constraint {
      doc /*
       * A system capability view shall define system capabilities
       * and their relationships.
       */
    }
  }

  // C8_SCYM has no SAF concern question, so this viewpoint has no concern
  // definition: an author who needs the mapping reads the requirement below.
  viewpoint def SystemCapabilityMappingViewpoint :> ConceptualDomainViewpoint {
    doc /*
     * SAF Conceptual Domain: System Capability Mapping Viewpoint.
     * Aspect: Traceability & Mapping
     * Source: https://saf.gfse.org/userdoc/viewpoints.html
     */
    require constraint {
      doc /*
       * A system capability mapping view shall show each system capability's
       * relationships to operational capabilities, system use cases, system
       * process activities and system requirements.
       */
    }
  }

  concern def FunctionalBehaviorConcern :> ConceptualDomainConcern {
    require constraint {
      doc /*
       * Reviewers need the functional responsibilities, information items,
       * flows, and sequencing for the feature increment to be visible
       * with requirement trace.
       */
    }
  }

  viewpoint def SystemFunctionalBreakdownStructureViewpoint :> ConceptualDomainViewpoint {
    doc /*
     * SAF Conceptual Domain: System Functional Breakdown Structure Viewpoint.
     * Aspect: Taxonomy & Structure
     * Source: https://saf.gfse.org/userdoc/viewpoints.html
     */
    require constraint {
      doc /*
       * A functional behavior view shall show functional responsibilities
       * (actions), information items, flows, and sequencing, with
       * requirement trace to functions.
       */
    }
  }

  concern def SystemProcessConcern :> ConceptualDomainConcern {
    require constraint {
      doc /*
       * Reviewers need behavior and process sequencing described for
       * the increment.
       */
    }
  }

  viewpoint def SystemProcessViewpoint :> ConceptualDomainViewpoint {
    doc /*
     * SAF Conceptual Domain: System Process Viewpoint.
     * Aspect: Process & Behavior
     * Source: https://saf.gfse.org/userdoc/viewpoints.html
     */
    require constraint {
      doc /*
       * A system process view shall describe behavior and process
       * sequencing for the increment, including state transitions
       * and temporal ordering.
       */
    }
  }

  concern def FunctionalInterfaceConcern :> ConceptualDomainConcern {
    require constraint {
      doc /*
       * Reviewers need the conceptual interfaces of the system for the
       * increment: its functional boundary ports, their typed items,
       * signal character and direction, and the functional chain that
       * owns them.
       */
    }
  }

  viewpoint def SystemInterfaceDefinitionViewpoint :> ConceptualDomainViewpoint {
    doc /*
     * SAF Conceptual Domain: System Interface Definition Viewpoint.
     * Aspect: Interface
     * Source: https://saf.gfse.org/userdoc/viewpoints.html
     */
    require constraint {
      doc /*
       * A functional interface view shall show boundary port definitions,
       * their typed items, signal character, direction, and the functional
       * chain that owns the ports.
       */
    }
  }

  concern def RequirementTraceConcern :> ConceptualDomainConcern {
    require constraint {
      doc /*
       * Reviewers need requirement candidates traced to stakeholder needs,
       * with verification methods and satisfaction status, including
       * what is not yet satisfied.
       */
    }
  }

  viewpoint def SystemRequirementDefinitionViewpoint :> ConceptualDomainViewpoint {
    doc /*
     * SAF Conceptual Domain: System Requirement Definition Viewpoint.
     * Aspect: Requirement
     * Source: https://saf.gfse.org/userdoc/viewpoints.html
     */
    require constraint {
      doc /*
       * A requirement definition view shall show requirement candidates
       * with their subject, stakeholder parameters, and required constraint
       * bodies.
       */
    }
  }

  viewpoint def SystemRequirementTraceabilityViewpoint :> ConceptualDomainViewpoint {
    doc /*
     * SAF Conceptual Domain: System Requirement Traceability Viewpoint.
     * Aspect: Traceability & Mapping
     * Source: https://saf.gfse.org/userdoc/viewpoints.html
     */
    require constraint {
      doc /*
       * A requirement traceability view shall show requirement candidates,
       * their stakeholder need sources, verification methods, and
       * satisfaction status, including explicitly unsatisfied items.
       */
    }
  }

  // ─── Conceptual Domain (continued) ───

  concern def ConceptualStructureConcern :> ConceptualDomainConcern {
    require constraint {
      doc /*
       * Reviewers need the conceptual system decomposition, conceptual element
       * responsibilities, and ownership boundaries to be visible.
       */
    }
  }

  viewpoint def SystemStructureDefinitionViewpoint :> ConceptualDomainViewpoint {
    doc /*
     * SAF Conceptual Domain: System Structure Definition Viewpoint.
     * Aspect: Taxonomy & Structure
     * Source: https://saf.gfse.org/userdoc/viewpoints.html
     */
    require constraint {
      doc /*
       * A logical structure view shall show the conceptual system boundary and
       * its hierarchical decomposition into conceptual elements responsible for
       * realizing system functions.
       */
    }
  }

  concern def ConceptualInternalExchangeConcern :> ConceptualDomainConcern {
    require constraint {
      doc /*
       * Reviewers need the typed conceptual interfaces, exchanges, directions,
       * and delegation from the conceptual system boundary to internal elements.
       */
    }
  }

  viewpoint def SystemInternalExchangeViewpoint :> ConceptualDomainViewpoint {
    doc /*
     * SAF Conceptual Domain: System Internal Exchange Viewpoint.
     * Aspect: Interaction & Collaboration
     * Source: https://saf.gfse.org/userdoc/viewpoints.html
     */
    require constraint {
      doc /*
       * A logical internal exchange view shall show the conceptual system
       * boundary, internal conceptual elements, connected interfaces, delegated
       * boundary interfaces, and exchanged logical items.
       */
    }
  }

  concern def ConceptualInternalInteractionConcern :> ConceptualDomainConcern {
    require constraint {
      doc /*
       * Reviewers need conceptual interactions (sequences, message ordering)
       * described for the increment.
       */
    }
  }

  viewpoint def SystemInternalInteractionViewpoint :> ConceptualDomainViewpoint {
    doc /*
     * SAF Conceptual Domain: System Internal Interaction Viewpoint.
     * Aspect: Interaction & Collaboration
     * Source: https://saf.gfse.org/userdoc/viewpoints.html
     */
    require constraint {
      doc /*
       * A logical internal interaction view shall show interactions
       * between conceptual elements, including message sequencing and
       * temporal relationships.
       */
    }
  }

  concern def ConceptualFunctionMappingConcern :> ConceptualDomainConcern {
    require constraint {
      doc /*
       * Reviewers need every system function allocated to one or more logical
       * elements without implying a physical or software implementation.
       */
    }
  }

  viewpoint def SystemFunctionMappingViewpoint :> ConceptualDomainViewpoint {
    doc /*
     * SAF Conceptual Domain: System Functional Mapping Viewpoint.
     * Aspect: Traceability & Mapping
     * Source: https://saf.gfse.org/userdoc/viewpoints.html
     */
    require constraint {
      doc /*
       * A logical functional mapping view shall show the allocation of system
       * functions and partial functions to conceptual system elements.
       */
    }
  }

  // ─── Physical Domain ───

  concern def PhysicalContextConcern :> PhysicalDomainConcern {
    require constraint {
      doc /*
       * Reviewer question: What is inside the candidate physical system,
       * which external physical systems interact with it, and where is the
       * physical context boundary?
       */
    }
  }

  viewpoint def PhysicalContextDefinitionViewpoint :> PhysicalDomainViewpoint {
    doc /*
     * SAF Physical Domain: P1_PCXD Physical Context Definition Viewpoint.
     * Aspect: Context & Exchange
     * Source: https://saf.gfse.org/userdoc/viewpoints.html
     */
    require constraint {
      doc /*
       * A physical context definition view shall show the candidate physical
       * system boundary, external physical systems, and their context roles.
       */
    }
  }

  concern def PhysicalContextExchangeConcern :> PhysicalDomainConcern {
    require constraint {
      doc /*
       * Reviewer question: What typed physical items cross the candidate
       * system boundary, and which context roles participate in each exchange?
       */
    }
  }

  viewpoint def PhysicalContextExchangeViewpoint :> PhysicalDomainViewpoint {
    doc /*
     * SAF Physical Domain: P1_PCXE Physical Context Exchange Viewpoint.
     * Aspect: Context & Exchange
     * Source: https://saf.gfse.org/userdoc/viewpoints.html
     */
    require constraint {
      doc /*
       * A physical context exchange view shall show boundary-crossing physical
       * exchanges, their typed items, and participating context roles. Textual
       * bindings and flows remain authoritative for exchange direction.
       */
    }
  }

  concern def PhysicalExchangeTypeConcern :> PhysicalDomainConcern {
    require constraint {
      doc /*
       * Reviewers need these questions answered for the increment: From which
       * conceptual item (energy, material, information) is a physical item
       * derived? Which kind of physical items (energy, material, information,
       * etc.) are defined for the physical architecture of the system?
       */
    }
  }

  viewpoint def PhysicalExchangeTypeDefinitionViewpoint :> PhysicalDomainViewpoint {
    doc /*
     * SAF Physical Domain: Physical Exchange Type Definition Viewpoint.
     * Aspect: Taxonomy & Structure
     * Source: https://saf.gfse.org/userdoc/viewpoints.html
     */
    require constraint {
      doc /*
       * A physical exchange type definition view shall show the physical item
       * types defined for the system's physical architecture, their properties
       * and relationships, and the conceptual item each physical type is
       * derived from.
       */
    }
  }


  concern def PhysicalStructureConcern :> PhysicalDomainConcern {
    require constraint {
      doc /*
       * Reviewer question: What physical hardware, software, and mechanical
       * elements make up the candidate system, and in which internal roles
       * are they used?
       */
    }
  }

  viewpoint def PhysicalStructureDefinitionViewpoint :> PhysicalDomainViewpoint {
    doc /*
     * SAF Physical Domain: P2_PSTD Physical Structure Definition Viewpoint.
     * Aspect: Taxonomy & Structure
     * Source: https://saf.gfse.org/userdoc/viewpoints.html
     */
    require constraint {
      doc /*
       * A physical structure definition view shall show the physical system
       * boundary and its breakdown into physical hardware, software, and
       * mechanical elements, including the roles in which elements are used.
       */
    }
  }

  concern def PhysicalInterfaceConcern :> PhysicalDomainConcern {
    require constraint {
      doc /*
       * Reviewer question: Which reusable physical interface and protocol
       * definitions apply, and what typed ports and exchanged item directions
       * do they define?
       */
    }
  }

  viewpoint def PhysicalInterfaceDefinitionViewpoint :> PhysicalDomainViewpoint {
    doc /*
     * SAF Physical Domain: P5_PIFD Physical Interface Definition Viewpoint.
     * Aspect: Interface
     * Source: https://saf.gfse.org/userdoc/viewpoints.html
     */
    require constraint {
      doc /*
       * A physical interface definition view shall show physical interface
       * definitions with typed ports, exchanged item directions, protocol
       * definitions, and compatibility or specialization relationships.
       */
    }
  }

  concern def PhysicalInternalExchangeConcern :> PhysicalDomainConcern {
    require constraint {
      doc /*
       * Reviewer question: Which internal physical roles exchange each typed
       * item? When an exchange crosses the subject boundary, which boundary
       * interface delegates it to an internal role?
       */
    }
  }

  viewpoint def PhysicalInternalExchangeViewpoint :> PhysicalDomainViewpoint {
    doc /*
     * SAF Physical Domain: P4_PIEX Physical Internal Exchange Viewpoint.
     * Aspect: Interaction & Collaboration
     * Source: https://saf.gfse.org/userdoc/viewpoints.html
     */
    require constraint {
      doc /*
       * A physical internal exchange view shall show internal physical roles
       * and typed exchanges. When an exchange crosses the subject boundary,
       * the view shall show the boundary interface and its delegation to an
       * internal role. Textual bindings and flows remain authoritative for
       * exchange direction.
       */
    }
  }

  concern def PhysicalContextInteractionConcern :> PhysicalDomainConcern {
    require constraint {
      doc /*
       * Reviewers need this question answered for the increment: What is the
       * sequence of interactions among the system and context elements on
       * physical level?
       */
    }
  }

  viewpoint def PhysicalContextInteractionViewpoint :> PhysicalDomainViewpoint {
    doc /*
     * SAF Physical Domain: Physical Context Interaction Viewpoint.
     * Aspect: Interaction & Collaboration
     * Source: https://saf.gfse.org/userdoc/viewpoints.html
     */
    require constraint {
      doc /*
       * A physical context interaction view shall show the sequence of
       * interactions between the system and its context elements at the
       * physical level, including the ordering and timing of the exchanges
       * across physical connections.
       */
    }
  }

  concern def PhysicalInternalInteractionConcern :> PhysicalDomainConcern {
    require constraint {
      doc /*
       * Reviewers need this question answered for the increment: What
       * sequences of exchanges occur between physical systems within the
       * system boundary through physical connections?
       */
    }
  }

  viewpoint def PhysicalInternalInteractionViewpoint :> PhysicalDomainViewpoint {
    doc /*
     * SAF Physical Domain: Physical Internal Interaction Viewpoint.
     * Aspect: Interaction & Collaboration
     * Source: https://saf.gfse.org/userdoc/viewpoints.html
     */
    require constraint {
      doc /*
       * A physical internal interaction view shall show the sequences of
       * exchanges between the physical systems inside the system boundary
       * across physical connections, including their ordering and timing.
       */
    }
  }

  concern def PhysicalFunctionalMappingConcern :> PhysicalDomainConcern {
    require constraint {
      doc /*
       * Reviewer question: Which physical/software elements realize which
       * system functions?
       */
    }
  }

  viewpoint def PhysicalFunctionalMappingViewpoint :> PhysicalDomainViewpoint {
    doc /*
     * SAF Physical Domain: P8_PFUM Physical Functional Mapping Viewpoint.
     * Aspect: Traceability & Mapping
     * Source: https://saf.gfse.org/userdoc/viewpoints.html
     */
    require constraint {
      doc /*
       * A physical functional mapping view shall show the allocation of
       * system functions to physical/software elements, including partial
       * and missing realizations.
       */
    }
  }

  concern def PhysicalLogicalMappingConcern :> PhysicalDomainConcern {
    require constraint {
      doc /*
       * Reviewer question: Which conceptual element roles are realized by which
       * physical element roles?
       */
    }
  }

  viewpoint def PhysicalLogicalMappingViewpoint :> PhysicalDomainViewpoint {
    doc /*
     * SAF Physical Domain: P8_PLOM Physical Logical Mapping Viewpoint.
     * Aspect: Traceability & Mapping
     * Source: https://saf.gfse.org/userdoc/viewpoints.html
     */
    require constraint {
      doc /*
       * A physical logical mapping view shall show logical and physical
       * element breakdowns and the realization relationships that identify
       * which physical element roles implement each conceptual element role.
       */
    }
  }

  concern def PhysicalLogicalItemMappingConcern :> PhysicalDomainConcern {
    require constraint {
      doc /*
       * Reviewer question: Which logical information items are realized by
       * which physical exchange items, and which similarly named or adjacent
       * physical items remain semantically distinct?
       */
    }
  }


  // ─── Conceptual Domain: Safety & Security aspect ───

  concern def AssetIdentificationConcern :> ConceptualDomainConcern {
    require constraint {
      doc /*
       * Reviewers need assets affected by the feature or toolchain to be
       * identified for safety and security analysis.
       */
    }
  }

  viewpoint def AssetIdentificationViewpoint :> ConceptualDomainViewpoint {
    doc /*
     * SAF Conceptual Domain: Asset Identification Viewpoint.
     * Aspect: Safety & Security
     * Source: https://saf.gfse.org/userdoc/viewpoints.html
     */
    require constraint {
      doc /*
       * An asset identification view shall identify assets affected by
       * the feature or toolchain, including safety-relevant and
       * security-relevant assets.
       */
    }
  }

  concern def SecurityContextConcern :> ConceptualDomainConcern {
    require constraint {
      doc /*
       * Reviewers need the security boundary and context identified for
       * the increment.
       */
    }
  }

  viewpoint def SecurityContextViewpoint :> ConceptualDomainViewpoint {
    doc /*
     * SAF Conceptual Domain: Security Context Viewpoint.
     * Aspect: Safety & Security
     * Source: https://saf.gfse.org/userdoc/viewpoints.html
     */
    require constraint {
      doc /*
       * A security context view shall identify the security boundary,
       * trusted/untrusted domains, and security-relevant context roles.
       */
    }
  }

  concern def SecurityRiskAnalysisConcern :> ConceptualDomainConcern {
    require constraint {
      doc /*
       * Reviewers need threat and risk analysis captured for the increment.
       */
    }
  }

  viewpoint def SecurityRiskAnalysisViewpoint :> ConceptualDomainViewpoint {
    doc /*
     * SAF Conceptual Domain: Security Risk Analysis Viewpoint.
     * Aspect: Safety & Security
     * Source: https://saf.gfse.org/userdoc/viewpoints.html
     */
    require constraint {
      doc /*
       * A security risk analysis view shall capture threats, risks,
       * mitigations, and residual risk for the increment.
       */
    }
  }

  concern def ThreatSzenarioConcern :> ConceptualDomainConcern {
    require constraint {
      doc /*
       * Reviewers need threat scenarios described for the increment.
       */
    }
  }

  viewpoint def ThreatSzenarioViewpoint :> ConceptualDomainViewpoint {
    doc /*
     * SAF Conceptual Domain: Threat Szenario Viewpoint.
     * Aspect: Safety & Security
     * Source: https://saf.gfse.org/userdoc/viewpoints.html
     */
    require constraint {
      doc /*
       * A threat scenario view shall describe threat scenarios with
       * attack vectors, affected assets, and potential impacts.
       */
    }
  }

  // ─── Architecture Management Domain (continued) ───

  concern def ArgumentationAssuranceConcern :> ArchitectureManagementDomainConcern {
    require constraint {
      doc /*
       * Reviewers need claims, arguments, evidence, and gaps linked
       * in an assurance argument for the increment.
       */
    }
  }

  viewpoint def ArgumentationAssuranceViewpoint :> ArchitectureManagementDomainViewpoint {
    doc /*
     * SAF Architecture Management Domain: Argumentation Assurance Viewpoint.
     * Aspect: Taxonomy & Structure
     * Source: https://saf.gfse.org/userdoc/viewpoints.html
     */
    require constraint {
      doc /*
       * An argumentation assurance view shall link claims, arguments,
       * evidence, and gaps in an assurance argument structure.
       */
    }
  }

  // ─── GfSE SAF-SysMLV2 additions ───
  concern def ImpactAnalysisConcern :> ConceptualDomainConcern {
    require constraint {
      doc /*
       * Reviewers need this question answered for the increment: Which
       * severity has the Loss of the Security Objectives?
       */
    }
  }

  viewpoint def ImpactAnalysisViewpoint :> ConceptualDomainViewpoint {
    doc /*
     * SAF Conceptual Domain: ImpactAnalysis Viewpoint
     * Aspect: Safety & Security
     * Source: https://saf.gfse.org/userdoc/viewpoints.html
     * GfSE frame bindings: SeverityOfLoss.
     */
    require constraint {
      doc /*
       * A ImpactAnalysisViewpoint view shall show the source-backed SAF frame bindings for the increment.
       */
    }
  }
  concern def OperationalExchangeTypeDefinitionConcern :> OperationalDomainConcern {
    require constraint {
      doc /*
       * Reviewers need this question answered for the increment: Why
       * types of exchange can exist between Operational Performers (i.e.,
       * flows of information, people, material, or energy)?
       */
    }
  }

  viewpoint def OperationalExchangeTypeDefinitionViewpoint :> OperationalDomainViewpoint {
    doc /*
     * SAF Operational Domain: Operational Exchange Type Definition Viewpoint.
     * Aspect: Taxonomy & Structure
     * Source: https://saf.gfse.org/userdoc/viewpoints.html
     */
    require constraint {
      doc /*
       * An operational exchange type definition view shall define the types of
       * exchange that can exist between operational performers and their
       * relationships.
       */
    }
  }
  concern def SystemContextInteractionConcern :> ConceptualDomainConcern {
    require constraint {
      doc /*
       * Reviewers need these questions answered for the increment: How is
       * the system being used or utilized and interacting with other
       * external systems to satisfy user needs? What is the necessary
       * response time for an interface or a service? What is the sequence
       * of interactions among the system and context elements on
       * conceptual level?
       */
    }
  }

  viewpoint def SystemContextInteractionViewpoint :> ConceptualDomainViewpoint {
    doc /*
     * SAF Conceptual Domain: SystemContextInteraction Viewpoint
     * Aspect: Interaction & Collaboration
     * Source: https://saf.gfse.org/userdoc/viewpoints.html
     * GfSE frame bindings: SystemUtilization, ResponseTimeRequirements, ConceptualInteractionSequence.
     */
    require constraint {
      doc /*
       * A SystemContextInteractionViewpoint view shall show the source-backed SAF frame bindings for the increment.
       */
    }
  }
  concern def OperationalContextExchangeConcern :> OperationalDomainConcern {
    require constraint {
      doc /*
       * Reviewers need this question answered for the increment: Which
       * operational exchanges do operational performers need to consume or
       * provide?
       */
    }
  }

  viewpoint def OperationalContextExchangeViewpoint :> OperationalDomainViewpoint {
    doc /*
     * SAF Operational Domain: OperationalContextExchange Viewpoint
     * Aspect: Context & Exchange
     * Source: https://saf.gfse.org/userdoc/viewpoints.html
     * GfSE frame bindings: OperationalContextExchanges.
     */
    require constraint {
      doc /*
       * A OperationalContextExchangeViewpoint view shall show the source-backed SAF frame bindings for the increment.
       */
    }
  }
  concern def SystemExchangeTypeDefinitionConcern :> ConceptualDomainConcern {
    require constraint {
      doc /*
       * Reviewers need this question answered for the increment: Which
       * kind of conceptual items (energy, material, information, etc.) are
       * used in the conceptual architecture of the system?
       */
    }
  }

  viewpoint def SystemExchangeTypeDefinitionViewpoint :> ConceptualDomainViewpoint {
    doc /*
     * SAF Conceptual Domain: System Exchange Type Definition Viewpoint.
     * Aspect: Taxonomy & Structure
     * Source: https://saf.gfse.org/userdoc/viewpoints.html
     */
    require constraint {
      doc /*
       * A system exchange type definition view shall define the conceptual item
       * types exchanged in the system's architecture, their relationships, and
       * the data types and units that functions and interfaces consume.
       */
    }
  }
  concern def SystemFunctionalRefinementConcern :> ConceptualDomainConcern {
    require constraint {
      doc /*
       * Reviewers need these questions answered for the increment: What
       * are the interactions and dependencies between the different
       * identified sub-functions? What is the breakdown of functions into
       * sub-functions? How are the system functions decomposed into
       * smaller, and more manageable sub-functions?
       */
    }
  }

  viewpoint def SystemFunctionalRefinementViewpoint :> ConceptualDomainViewpoint {
    doc /*
     * SAF Conceptual Domain: SystemFunctionalRefinement Viewpoint
     * Aspect: Process & Behavior
     * Source: https://saf.gfse.org/userdoc/viewpoints.html
     * GfSE frame bindings: SubfunctionInteractions, SystemFunctionBreakdown, SystemFunctionDecomposition.
     */
    require constraint {
      doc /*
       * A SystemFunctionalRefinementViewpoint view shall show the source-backed SAF frame bindings for the increment.
       */
    }
  }
  concern def SystemStateConcern :> ConceptualDomainConcern {
    require constraint {
      doc /*
       * Reviewers need these questions answered for the increment: Which
       * modes and states does the system have? Which system functions are
       * dependent on a system's mode or state?
       */
    }
  }

  viewpoint def SystemStateViewpoint :> ConceptualDomainViewpoint {
    doc /*
     * SAF Conceptual Domain: SystemState Viewpoint
     * Aspect: Process & Behavior
     * Source: https://saf.gfse.org/userdoc/viewpoints.html
     * GfSE frame bindings: SystemModes, SystemFunctionsDependentOnModes.
     */
    require constraint {
      doc /*
       * A SystemStateViewpoint view shall show the source-backed SAF frame bindings for the increment.
       */
    }
  }
  concern def OperationalContextInteractionConcern :> OperationalDomainConcern {
    require constraint {
      doc /*
       * Reviewers need this question answered for the increment: What
       * possible threads of operational process activities have to be
       * carried out to achieve the operational story main and alternative
       * goals?
       */
    }
  }

  viewpoint def OperationalContextInteractionViewpoint :> OperationalDomainViewpoint {
    doc /*
     * SAF Operational Domain: OperationalContextInteraction Viewpoint
     * Aspect: Interaction & Collaboration
     * Source: https://saf.gfse.org/userdoc/viewpoints.html
     * GfSE frame bindings: OperationalProcessThreads.
     */
    require constraint {
      doc /*
       * A OperationalContextInteractionViewpoint view shall show the source-backed SAF frame bindings for the increment.
       */
    }
  }
  concern def GridDefinitionConcern :> ArchitectureManagementDomainConcern {
    require constraint {
      doc /*
       * Reviewers need these questions answered for the increment: Which
       * viewpoints are used in the system model? Which views of the
       * frameworks viewpoints are present in the system model?
       */
    }
  }

  viewpoint def GridDefinitionViewpoint :> ArchitectureManagementDomainViewpoint {
    doc /*
     * SAF Architecture Management Domain: GridDefinition Viewpoint
     * Aspect: Taxonomy & Structure
     * Source: https://saf.gfse.org/userdoc/viewpoints.html
     * GfSE frame bindings: ViewpointsUsedInSystemModel, FrameworkViewpoints.
     */
    require constraint {
      doc /*
       * A GridDefinitionViewpoint view shall show the source-backed SAF frame bindings for the increment.
       */
    }
  }
  concern def FrameworkConceptDefinitionConcern :> SAFDevelopmentDomainConcern {
    require constraint {
      doc /*
       * Reviewers need these questions answered for the increment: What
       * are the relations between systems engineering concepts covered by
       * the framework? What are the constraints related to SE concepts
       * covered by the framework? Which systems engineering concepts are
       * covered by the framework?
       */
    }
  }

  viewpoint def FrameworkConceptDefinitionViewpoint :> SAFDevelopmentDomainViewpoint {
    doc /*
     * SAF Development Domain: FrameworkConceptDefinition Viewpoint
     * Aspect: Taxonomy & Structure
     * Source: https://saf.gfse.org/userdoc/viewpoints.html
     * GfSE frame bindings: RelationsBetweenSEConcepts, ConstraintsOnSEConcepts, SEConceptsCovered.
     */
    require constraint {
      doc /*
       * A FrameworkConceptDefinitionViewpoint view shall show the source-backed SAF frame bindings for the increment.
       */
    }
  }
  concern def FrameworkConcernOverviewConcern :> SAFDevelopmentDomainConcern {
    require constraint {
      doc /*
       * Reviewers need these questions answered for the increment: What is
       * the definition of rows (domains) in the framework's grid? What is
       * the definition of columns (aspects) in the framework's grid? Which
       * columns and rows does the framework's grid have? Where is a
       * viewpoint of the framework located in the framework's grid? What
       * is the maturity state of viewpoints in the framework? Which
       * viewpoints are available in the framework?
       */
    }
  }

  viewpoint def FrameworkViewpointOverviewViewpoint :> SAFDevelopmentDomainViewpoint {
    doc /*
     * SAF Development Domain: Framework ViewpointOverview Viewpoint
     * Aspect: Taxonomy & Structure
     * Source: https://saf.gfse.org/userdoc/viewpoints.html
     * GfSE frame bindings: DefinitionOfGridRows, DefinitionOfGridColumns, FrameworkGridStructure, ViewpointLocationInGrid, MaturityOfViewpoints, AvailableViewpoints.
     */
    require constraint {
      doc /*
       * A FrameworkViewpointOverviewViewpoint view shall show the source-backed SAF frame bindings for the increment.
       */
    }
  }
  concern def FrameworkStakeholderandConcernDefinitionConcern :> SAFDevelopmentDomainConcern {
    require constraint {
      doc /*
       * Reviewers need these questions answered for the increment: Which
       * concerns does an architecture framework stakeholder have? Who are
       * the architecture framework stakeholders of the framework's
       * viewpoints?
       */
    }
  }

  viewpoint def FrameworkStakeholderandConcernDefinitionViewpoint :> SAFDevelopmentDomainViewpoint {
    doc /*
     * SAF Development Domain: FrameworkStakeholderandConcernDefinition Viewpoint
     * Aspect: Taxonomy & Structure
     * Source: https://saf.gfse.org/userdoc/viewpoints.html
     * GfSE frame bindings: StakeholderConcerns, FrameworkStakeholders, StakeholderConcernsReasons.
     */
    require constraint {
      doc /*
       * A FrameworkStakeholderandConcernDefinitionViewpoint view shall show the source-backed SAF frame bindings for the increment.
       */
    }
  }
  concern def FrameworkConcernDefinitionConcern :> SAFDevelopmentDomainConcern {
    require constraint {
      doc /*
       * Reviewers need these questions answered for the increment: Which
       * systems engineering concepts are exposed within a viewpoint of the
       * framework? Which concerns are framed by a viewpoint of the
       * framework? What is the definition of a viewpoint of the framework?
       * Where is a viewpoint of the framework located in the framework's
       * grid? What is the purpose of a viewpoint in the framework? Which
       * presentations are available for a viewpoint in the framework?
       * Which dependencies to other viewpoints exist for a viewpoint of
       * the framework? How does a viewpoint of the framework support the
       * processes and best practices of systems engineering standards?
       */
    }
  }

  viewpoint def FrameworkViewpointDefinitionViewpoint :> SAFDevelopmentDomainViewpoint {
    doc /*
     * SAF Development Domain: Framework ViewpointDefinition Viewpoint
     * Aspect: Taxonomy & Structure
     * Source: https://saf.gfse.org/userdoc/viewpoints.html
     * GfSE frame bindings: ConceptsExposedInViewpoints, ConcernsFramedByViewpoints, DefinitionOfViewpoints, ViewpointLocationInGrid, ViewpointPurpose, ViewpointPresentations, ViewpointDependencies, SupportForSEStandards.
     */
    require constraint {
      doc /*
       * A FrameworkViewpointDefinitionViewpoint view shall show the source-backed SAF frame bindings for the increment.
       */
    }
  }
  concern def FrameworkConcernImplementationConcern :> SAFDevelopmentDomainConcern {
    require constraint {
      doc /*
       * Reviewers need these questions answered for the increment: What is
       * the implementation of the framework's concepts? How is a viewpoint
       * implemented (which stereotypes/model elements are used)?
       */
    }
  }

  viewpoint def FrameworkViewpointImplementationViewpoint :> SAFDevelopmentDomainViewpoint {
    doc /*
     * SAF Development Domain: Framework ViewpointImplementation Viewpoint
     * Aspect: Taxonomy & Structure
     * Source: https://saf.gfse.org/userdoc/viewpoints.html
     * GfSE frame bindings: ImplementationOfFrameworkConcepts, ViewpointImplementation.
     */
    require constraint {
      doc /*
       * A FrameworkViewpointImplementationViewpoint view shall show the source-backed SAF frame bindings for the increment.
       */
    }
  }
  concern def FrameworkImplementationTraceabilityConcern :> SAFDevelopmentDomainConcern {
    require constraint {
      doc /*
       * Reviewers need these questions answered for the increment: What is
       * the implementation of the framework's concepts? What are the
       * framework's model elements to be used in system models?
       */
    }
  }

  viewpoint def FrameworkImplementationTraceabilityViewpoint :> SAFDevelopmentDomainViewpoint {
    doc /*
     * SAF Development Domain: FrameworkImplementationTraceability Viewpoint
     * Aspect: Traceability & Mapping
     * Source: https://saf.gfse.org/userdoc/viewpoints.html
     * GfSE frame bindings: ImplementationOfFrameworkConcepts, FrameworkModelElements.
     */
    require constraint {
      doc /*
       * A FrameworkImplementationTraceabilityViewpoint view shall show the source-backed SAF frame bindings for the increment.
       */
    }
  }
  concern def FrameworkStereotypeOverviewConcern :> SAFDevelopmentDomainConcern {
    require constraint {
      doc /*
       * Reviewers need this question answered for the increment: What are
       * the framework's model elements to be used in system models?
       */
    }
  }

  viewpoint def FrameworkStereotypeOverviewViewpoint :> SAFDevelopmentDomainViewpoint {
    doc /*
     * SAF Development Domain: FrameworkStereotypeOverview Viewpoint
     * Aspect: Taxonomy & Structure
     * Source: https://saf.gfse.org/userdoc/viewpoints.html
     * GfSE frame bindings: FrameworkModelElements.
     */
    require constraint {
      doc /*
       * A FrameworkStereotypeOverviewViewpoint view shall show the source-backed SAF frame bindings for the increment.
       */
    }
  }
  concern def OperationalPerformerDefinitionConcern :> OperationalDomainConcern {
    require constraint {
      doc /*
       * Reviewers need these questions answered for the increment: What are
       * the relationships between the partys involved in the operation of the
       * intended solution? What partys of the organization, enterprise, or
       * operational entity are needed to achieve an intended operational
       * capability?
       */
    }
  }

  viewpoint def OperationalPerformerDefinitionViewpoint :> OperationalDomainViewpoint {
    doc /*
     * SAF Operational Domain: Operational Performer Definition Viewpoint.
     * Aspect: Taxonomy & Structure
     * Source: https://saf.gfse.org/userdoc/viewpoints.html
     */
    require constraint {
      doc /*
       * An operational performer definition view shall show the taxonomy of the
       * identified operational performers and their relationships, where the
       * operation of the intended solution calls for them.
       */
    }
  }
  concern def OperationalCapabilityMappingConcern :> OperationalDomainConcern {
    require constraint {
      doc /*
       * Reviewers need this question answered for the increment: How do
       * operational capabilities relate to operational stories,
       * operational activities and operational performers?
       */
    }
  }

  viewpoint def OperationalCapabilityMappingViewpoint :> OperationalDomainViewpoint {
    doc /*
     * SAF Operational Domain: OperationalCapabilityMapping Viewpoint
     * Aspect: Traceability & Mapping
     * Source: https://saf.gfse.org/userdoc/viewpoints.html
     * GfSE frame bindings: OperationalCapabilityRelationships.
     */
    require constraint {
      doc /*
       * A OperationalCapabilityMappingViewpoint view shall show the source-backed SAF frame bindings for the increment.
       */
    }
  }
  concern def OperationalProcessMappingConcern :> OperationalDomainConcern {
    require constraint {
      doc /*
       * Reviewers need this question answered for the increment: How do
       * operational processes relate to operational stories and
       * operational performers?
       */
    }
  }

  viewpoint def OperationalProcessMappingViewpoint :> OperationalDomainViewpoint {
    doc /*
     * SAF Operational Domain: OperationalProcessMapping Viewpoint
     * Aspect: Traceability & Mapping
     * Source: https://saf.gfse.org/userdoc/viewpoints.html
     * GfSE frame bindings: OperationalProcessRelationships.
     */
    require constraint {
      doc /*
       * A OperationalProcessMappingViewpoint view shall show the source-backed SAF frame bindings for the increment.
       */
    }
  }
}
