/*
 * DE4SDV method process — iteration sequence of the DE4SDV increment workflow.
 *
 * This package models the 12-phase increment workflow from
 * methodologies/sysmod-sysmlv2/increment-workflow.md as a SysML v2 model.
 * The phase sequence and feedback loops are documented in
 * methodologies/sysmod-sysmlv2/process-mapping.md (PR #74) as a mermaid
 * diagram. This SysML model provides the structured data: the phase
 * enumeration (each phase's documentation names its SAF domain), the
 * recurring logical-to-software signal-mapping control, and the increment
 * size guidance.
 *
 * Source: methodologies/sysmod-sysmlv2/increment-workflow.md
 *         methodologies/sysmod-sysmlv2/process-mapping.md
 */

package DE4SDV_MethodProcess {
  private import Views::*;
  private import SAF_Viewpoints::*;
  private import DE4SDV_Stakeholders::*;

  /* ─── Method phases ─── */

  enum def MethodPhase {
    doc /* One of the 12 phases of the DE4SDV increment workflow. */

    phase0_incrementFraming {
      doc /* What are we changing or learning? Architecture Management domain. */
    }
    phase1_concernFraming {
      doc /* Who cares and why? Architecture Management/Operational domain. */
    }
    phase2_operationalContext {
      doc /* What happens in the world? Operational domain. */
    }
    phase3_capabilityClassification {
      doc /* Which characteristics distinguish member products? DE4SDV ontology. */
    }
    phase4_needs {
      doc /* What stakeholder needs exist? Operational domain. */
    }
    phase5_requirements {
      doc /* What shall the system do? Conceptual domain. */
    }
    phase6_functionalArchitecture {
      doc /* What functions, flows, states, interfaces? Conceptual domain. */
    }
    phase7_logicalArchitecture {
      doc /* What technology-independent logical elements realize functions? Conceptual domain. */
    }
    phase8_physicalRealization {
      doc /* What software/hardware realizes the logical design, and which applicable logical or semantic signals cross into typed software contracts? Physical domain. */
    }
    phase9_variabilityConfiguration {
      doc /* How does this vary across member products? DE4SDV product-line layer. */
    }
    phase10_vvEvidence {
      doc /* How will satisfaction be checked? Architecture Management/Conceptual domain. */
    }
    phase11_baseline {
      doc /* What is accepted, deferred, or invalidated, and which published views show it? Architecture Management domain. */
    }
  }

  /* ─── Scoped trace obligations ─── */
  /* Per-increment obligations live in DE4SDV_IncrementWorkflow. No universal
   * category-string chain is active. Increment framing always applies; each
   * later step applies when the increment charter lists its phase, and the
   * steps of those phases declare the checks. Source relationships and
   * artifact identities, not populated shells, witness the required traces. */

  /* ─── Recurring system-to-software signal mapping control ─── */

  enum def SignalMappingDisposition {
    doc /* The disposition of a logical-to-software signal mapping (mapped, candidate, deferred, or notApplicable). */
    mapped {
      doc /* The applicable logical/semantic signal has an accepted software-contract mapping for the declared scope. */
    }
    candidate {
      doc /* A reference or proposed contract mapping exists, but the selected platform realization remains open. */
    }
    deferred {
      doc /* The mapping is known to be needed but is intentionally postponed with an owned gap and next action. */
    }
    notApplicable {
      doc /* The signal does not cross the applicable software/physical boundary; the record's evidenceOrGap states why. */
    }
  }

  item def LogicalToSoftwareSignalMappingRecord {
    private doc ontologyDefinition /* A control record for a logical or semantic information item crossing into a software,
     * service, topic, API, or physical boundary; preserves trace and review obligations
     * without claiming runtime interoperability. */
    doc /*
     * Reusable control-record shape for an interface-bearing logical or
     * semantic information item crossing into a software, service, topic, API,
     * or physical boundary. Exact .proto/.vsidl fields and runtime observations
     * remain in their authoritative external artifacts; this record preserves
     * the stable trace and review obligations. The record's short name is its
     * mapping ID.
     */
    attribute semanticSource : ScalarValues::String {
      doc /* For an item that is no VSS-typed vehicle signal: what it is, and why no VSS signal applies. A vehicle signal names its source by its VSS typing instead; the owning mapping's target, the typed ports and the connections give the endpoints and the direction. */
    }
    attribute softwareContractArtifact : ScalarValues::String;
    attribute softwareContractMessage : ScalarValues::String;
    attribute softwareContractField : ScalarValues::String;
    attribute dataTypeAndUnit : ScalarValues::String;
    attribute timingQualityAndState : ScalarValues::String;
    attribute transformationRule : ScalarValues::String;
    attribute disposition : SignalMappingDisposition;
    attribute owner : ScalarValues::String;
    attribute nextAction : ScalarValues::String;
    attribute evidenceOrGap : ScalarValues::String;
  }

  allocation def SystemToSoftwareSignalMappingCandidate {
    private doc ontologyDefinition /* A reusable non-claiming allocation relationship from a logical/function signal
     * responsibility to a concrete software or adapter signal endpoint; the allocation
     * alone never proves field identity or runtime interoperability. */
    doc /*
     * Reusable non-claiming allocation relationship from a logical/function
     * signal responsibility to a concrete software/adapter signal endpoint.
     * A specialization must still provide the typed payload/port, contract
     * mapping record, transformation, status, owner, next action, and evidence
     * or gap. The allocation alone never proves field identity or runtime
     * interoperability.
     */
  }

  /* ─── Increment size guidance ─── */

  enum def IncrementSize {
    doc /* Size guidance for an increment (XS correction, S slice, M cross-viewpoint, L end-to-end baseline). */
    XS {
      doc /* One correction or trace link. */
    }
    S {
      doc /* One feature/scenario/context slice. */
    }
    M {
      doc /* Cross-viewpoint increment. */
    }
    L {
      doc /* End-to-end feature baseline. */
    }
  }

  /* ─── Assurance view for the method process itself ─── */

  concern methodProcessAssuranceConcern : ArgumentationAssuranceConcern {
    doc /*
     * Reviewers need the DE4SDV method process to be visible: the phases
     * with their SAF domains, the recurring logical-to-software
     * signal-mapping control, and the increment size guidance.
     */
    subject;
    stakeholder systemsEngineer : SystemsEngineer;
    stakeholder reviewer : OpenSourceReviewer;
  }

  view methodProcessView {
    viewpoint selectedMethodProcessAssuranceViewpoint : ArgumentationAssuranceViewpoint {
      frame methodProcessAssuranceConcern;
    }

    expose DE4SDV_MethodProcess::*;
    render asTreeDiagram;
  }
}
