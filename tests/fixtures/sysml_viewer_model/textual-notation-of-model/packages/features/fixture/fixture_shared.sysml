/*
 * Shared type definitions for the SysML HTML viewer tests.
 * Hand-authored test data — NOT a copy of any real DE4SDV model file.
 */

package FixtureShared {
  part def SignalInputPort;
  part def SignalOutputPort;
  part def FixtureSharedType;
}
