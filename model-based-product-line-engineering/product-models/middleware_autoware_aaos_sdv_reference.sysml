/*
 * Derived platform-stack product-model projection — DO NOT EDIT.
 * Generated by configure_variant.py from a PLEML configuration receipt.
 * This is not a complete member-product specification.
 * Shared-assets source baseline: git-blob:59f17075eae082a430f9232efcfe203724154f76:textual-notation-of-model/packages/architecture/sdv_platform_stack.sysml (content-addressed)
 * Shared-assets model: textual-notation-of-model/packages/architecture/sdv_platform_stack.sysml
 * Shared-assets model SHA-256: 616dfce419346bf31cdfd9db1b54a3ecc99c577ad808d4e70dc22bdb96493557
 * Receipt: model-based-product-line-engineering/feature-models/receipts/sdv_product_line.receipt.json
 * Receipt SHA-256: b5fe031941baa6f43d7b8ab2c48b5d0bee992c2afe53d1cb4d1f21fc56bdcae1
 * Elements SHA-256: a187a596041311715bd7269e638d33da4275932512576bb5ee31ae5dad0259e5
 * Feature configuration: model-based-product-line-engineering/feature-configurations/middleware_autoware_aaos_sdv_reference.sysml (middlewareAutowareAAOSSDVReference)
 * Feature configuration SHA-256: d18207b51603af37e9f4f1037bf5789c11e4f7a496e04fc65294f827536f10ad
 * PLEML feature model: model-based-product-line-engineering/feature-models/sdv_product_line.sysml
 * PLEML feature model SHA-256: a259b8a6736d81f204a7eaeb9f7a2bb13729a8658d1513f66eb40388dd91321f
 */

private import DE4SDV_SDVPlatformStack::SDVPlatformStack;

part def MiddlewareAutowareAAOSSDVReference :> SDVPlatformStack {
  doc /*
   * Derived platform-stack projection from PLEML configuration receipt.
   * Planned Autoware + AAOS SDV middleware reference member on one SoC, with LiDAR and camera perception. Autoware runs on its ROS 2/Linux application runtime on the main side, which is also the KVM host. The AAOS SDV middleware runs in the AAOS SDV guest under KVM, the SDV Core platform domain with no HMI display (owner decisions D3 of 2026-10-21 and D2 V3 of 2026-10-22). Cross-domain transport remains unresolved. This configuration and its projection do not prove provider, generated binding, discovery, transport, adapter deployment, ROS 2 publication, Autoware observation, safety, compliance, or runtime interoperability.
   * Configuration management note: this is MW-CONFIG-001, and the identity is not renumbered. Until INC-MW-011 phase 9 its single operating-system selection was Android HLOS, and it had no guest side. E-MW-011 to E-MW-014, BL-MW-010-P12 and CLM-MW-010-01 were retained against that pre-correction content, at the INC-MW-010 baseline revision b8170f6953567b07164b8c02be05be137f8047f0. Their records are not edited.
   *
   * Variant selections:
   *   vehicleApplication = autoware
   *   middleware = androidSDV
   *   osPlatform = linux
   *   hypervisor = kvm
   *   guestOSPlatform = android
   *   guestMiddleware = androidSDV
   *   applicationMiddlewareAdapter = autowareToAAOSSDV (derived by D-ASSET-APPLICATION-MIDDLEWARE-ADAPTER)
   *
   * Feature selections outside this projection (not resolved in SysML):
   *   sensingBoundary.perceptionSensors = lidar, camera
   *   capabilities.pedestrianDetection = disabled
   *   capabilities.bicycleDetection = disabled
   *   capabilities.adaptiveCruiseControl = disabled
   *   capabilities.laneKeepAssist = disabled
   *   capabilities.hmiDisplay = disabled
   */

  part :>> vehicleApplication = vehicleApplication::autoware;
  part :>> middleware = middleware::androidSDV;
  part :>> osPlatform = osPlatform::linux;
  part :>> hypervisor = hypervisor::kvm;
  part :>> guestOSPlatform = guestOSPlatform::android;
  part :>> guestMiddleware = guestMiddleware::androidSDV;
  part :>> applicationMiddlewareAdapter = applicationMiddlewareAdapter::autowareToAAOSSDV;
}
