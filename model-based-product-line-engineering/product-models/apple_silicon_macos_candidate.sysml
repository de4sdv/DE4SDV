/*
 * Derived engineering execution-environment product-model projection — DO NOT EDIT.
 * Generated by configure_variant.py from a PLEML configuration receipt.
 * This is not a complete member-product specification.
 * Shared-assets source baseline: git-blob:998c47e198d51e8bcf0db46f90f48edffa5506cc:textual-notation-of-model/packages/architecture/execution_environments.sysml (content-addressed)
 * Shared-assets model: textual-notation-of-model/packages/architecture/execution_environments.sysml
 * Shared-assets model SHA-256: f35675c21dced2604c813b4a366b0cfbdd6a410ccb58539cb387188e89e538fc
 * Receipt: model-based-product-line-engineering/feature-models/receipts/engineering_execution_environments.receipt.json
 * Receipt SHA-256: 8ea9ac8d13addc4f540bb894a073480e3ed5652dd8be426db0f7b9091b68d278
 * Elements SHA-256: a187a596041311715bd7269e638d33da4275932512576bb5ee31ae5dad0259e5
 * Feature configuration: model-based-product-line-engineering/feature-configurations/apple_silicon_macos_candidate.sysml (appleSiliconMacOSCandidate)
 * Feature configuration SHA-256: 4adceab22e25e3c4a5a21e6c54e8bc37c00ce1ed260449f01ef44abb0fd65a23
 * PLEML feature model: model-based-product-line-engineering/feature-models/engineering_execution_environments.sysml
 * PLEML feature model SHA-256: 389d5cd4f7ae7e834b3a6705213d2b814255f17b5d8922b7e67244ae800ed1ef
 */

private import DE4SDV_ExecutionEnvironments::EngineeringExecutionEnvironment;

part def AppleSiliconMacOSCandidate :> EngineeringExecutionEnvironment {
  doc /*
   * Derived engineering execution-environment projection from PLEML configuration receipt.
   * Planned and unverified System 2 candidate for an Apple Silicon M-series Mac running macOS with a virtualized Linux/ARM64 OCI environment. No specific Mac, container implementation, or DE4SDV runtime result is claimed.
   *
   * Variant selections:
   *   computeNode = appleSiliconMac
   *   operatingSystem = macOSAppleSilicon
   *   executionRuntime = virtualizedLinuxArm64OCIOnMacOS
   */

  part :>> computeNode = computeNode::appleSiliconMac;
  part :>> operatingSystem = operatingSystem::macOSAppleSilicon;
  part :>> executionRuntime = executionRuntime::virtualizedLinuxArm64OCIOnMacOS;
}
