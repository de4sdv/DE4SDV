/*
 * Derived vehicle-target execution-environment product-model projection — DO NOT EDIT.
 * Generated by configure_variant.py from a PLEML configuration receipt.
 * This is not a complete member-product specification.
 * Shared-assets source baseline: git-blob:998c47e198d51e8bcf0db46f90f48edffa5506cc:textual-notation-of-model/packages/architecture/execution_environments.sysml (content-addressed)
 * Shared-assets model: textual-notation-of-model/packages/architecture/execution_environments.sysml
 * Shared-assets model SHA-256: f35675c21dced2604c813b4a366b0cfbdd6a410ccb58539cb387188e89e538fc
 * Receipt: model-based-product-line-engineering/feature-models/receipts/vehicle_execution_environments.receipt.json
 * Receipt SHA-256: 1bda72f8f78e27beae0b38a4ae0f391d85094f5e77a70894764521930b5ec3c6
 * Elements SHA-256: a187a596041311715bd7269e638d33da4275932512576bb5ee31ae5dad0259e5
 * Feature configuration: model-based-product-line-engineering/feature-configurations/nxp_zephyr_vehicle_target_candidate.sysml (nxpZephyrVehicleTargetCandidate)
 * Feature configuration SHA-256: 73159664de143098d2f4a9d46f8aea6ec47aa401840d528c828610bde0f23e10
 * PLEML feature model: model-based-product-line-engineering/feature-models/vehicle_execution_environments.sysml
 * PLEML feature model SHA-256: 638ad3ead7b6f1a4006a3ccd4b5c693d1ac946407a0794f3234538dfd6dfb79b
 */

private import DE4SDV_ExecutionEnvironments::VehicleTargetExecutionEnvironment;

part def NXPZephyrVehicleTargetCandidate :> VehicleTargetExecutionEnvironment {
  doc /*
   * Derived vehicle-target execution-environment projection from PLEML configuration receipt.
   * Planned and unverified System 1 vehicle-target candidate combining an unresolved NXP board/SoC with native Zephyr execution. This does not claim that the Autoware ROS 2 application composition executes on Zephyr; software allocation and vehicle-platform interfaces remain unresolved.
   *
   * Variant selections:
   *   computeNode = nxpVehicleCompute
   *   operatingSystem = zephyr
   *   executionRuntime = nativeZephyr
   */

  part :>> computeNode = computeNode::nxpVehicleCompute;
  part :>> operatingSystem = operatingSystem::zephyr;
  part :>> executionRuntime = executionRuntime::nativeZephyr;
}
