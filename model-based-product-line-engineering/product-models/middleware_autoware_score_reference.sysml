/*
 * Derived platform-stack product-model projection — DO NOT EDIT.
 * Generated by configure_variant.py from a PLEML configuration receipt.
 * This is not a complete member-product specification.
 * Shared-assets source baseline: git-blob:59f17075eae082a430f9232efcfe203724154f76:textual-notation-of-model/packages/architecture/sdv_platform_stack.sysml (content-addressed)
 * Shared-assets model: textual-notation-of-model/packages/architecture/sdv_platform_stack.sysml
 * Shared-assets model SHA-256: 616dfce419346bf31cdfd9db1b54a3ecc99c577ad808d4e70dc22bdb96493557
 * Receipt: model-based-product-line-engineering/feature-models/receipts/sdv_product_line.receipt.json
 * Receipt SHA-256: b5fe031941baa6f43d7b8ab2c48b5d0bee992c2afe53d1cb4d1f21fc56bdcae1
 * Elements SHA-256: a187a596041311715bd7269e638d33da4275932512576bb5ee31ae5dad0259e5
 * Feature configuration: model-based-product-line-engineering/feature-configurations/middleware_autoware_score_reference.sysml (middlewareAutowareSCOREReference)
 * Feature configuration SHA-256: 41ec74ab7c1aaf5318d7c669dc82ba0ef9c350b4f60f5ca5529cdbfca63ac561
 * PLEML feature model: model-based-product-line-engineering/feature-models/sdv_product_line.sysml
 * PLEML feature model SHA-256: a259b8a6736d81f204a7eaeb9f7a2bb13729a8658d1513f66eb40388dd91321f
 */

private import DE4SDV_SDVPlatformStack::SDVPlatformStack;

part def MiddlewareAutowareSCOREReference :> SDVPlatformStack {
  doc /*
   * Derived platform-stack projection from PLEML configuration receipt.
   * Eclipse S-CORE reference configuration on one SoC: Autoware on Eclipse S-CORE on Linux on the main side, which is also the KVM host, and an AAOS SDV guest under KVM that shows the HMI on a display. Vehicle-target AEBS only (no pedestrian/bicycle detection).
   *
   * Variant selections:
   *   vehicleApplication = autoware
   *   middleware = eclipseSCORE
   *   osPlatform = linux
   *   hypervisor = kvm
   *   guestOSPlatform = android
   *   guestMiddleware = androidSDV
   *   applicationMiddlewareAdapter = autowareToSCORE (derived by D-ASSET-APPLICATION-MIDDLEWARE-ADAPTER)
   *
   * Feature selections outside this projection (not resolved in SysML):
   *   sensingBoundary.perceptionSensors = lidar, camera
   *   capabilities.pedestrianDetection = disabled
   *   capabilities.bicycleDetection = disabled
   *   capabilities.adaptiveCruiseControl = disabled
   *   capabilities.laneKeepAssist = disabled
   *   capabilities.hmiDisplay = enabled
   */

  part :>> vehicleApplication = vehicleApplication::autoware;
  part :>> middleware = middleware::eclipseSCORE;
  part :>> osPlatform = osPlatform::linux;
  part :>> hypervisor = hypervisor::kvm;
  part :>> guestOSPlatform = guestOSPlatform::android;
  part :>> guestMiddleware = guestMiddleware::androidSDV;
  part :>> applicationMiddlewareAdapter = applicationMiddlewareAdapter::autowareToSCORE;
}
