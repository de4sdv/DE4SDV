/*
 * Derived platform-stack product-model projection — DO NOT EDIT.
 * Generated by configure_variant.py from a PLEML configuration receipt.
 * This is not a complete member-product specification.
 * Shared-assets source baseline: git-blob:59f17075eae082a430f9232efcfe203724154f76:textual-notation-of-model/packages/architecture/sdv_platform_stack.sysml (content-addressed)
 * Shared-assets model: textual-notation-of-model/packages/architecture/sdv_platform_stack.sysml
 * Shared-assets model SHA-256: 616dfce419346bf31cdfd9db1b54a3ecc99c577ad808d4e70dc22bdb96493557
 * Receipt: model-based-product-line-engineering/feature-models/receipts/sdv_product_line.receipt.json
 * Receipt SHA-256: b5fe031941baa6f43d7b8ab2c48b5d0bee992c2afe53d1cb4d1f21fc56bdcae1
 * Elements SHA-256: a187a596041311715bd7269e638d33da4275932512576bb5ee31ae5dad0259e5
 * Feature configuration: model-based-product-line-engineering/feature-configurations/closed_loop_driving_autoe2e_score_reference.sysml (closedLoopDrivingAutoE2ESCOREReference)
 * Feature configuration SHA-256: beff58616091361d0f4df152611e71b5bde523cc08aebd8c86675830f03049c3
 * PLEML feature model: model-based-product-line-engineering/feature-models/sdv_product_line.sysml
 * PLEML feature model SHA-256: a259b8a6736d81f204a7eaeb9f7a2bb13729a8658d1513f66eb40388dd91321f
 */

private import DE4SDV_SDVPlatformStack::SDVPlatformStack;

part def ClosedLoopDrivingAutoE2ESCOREReference :> SDVPlatformStack {
  doc /*
   * Derived platform-stack projection from PLEML configuration receipt.
   * Closed-loop driving reference configuration on one SoC: AutoE2E on Eclipse S-CORE on Linux on the main side, which is also the KVM host, and an AAOS SDV guest under KVM that shows the driving system's operational state on a display. Cameras only: AutoE2E plans from camera images, so LiDAR and radar are absent (C012 requires the camera and leaves the others selectable). Vehicle-target AEBS only (no pedestrian/bicycle detection).
   *
   * Variant selections:
   *   vehicleApplication = autoE2E
   *   middleware = eclipseSCORE
   *   osPlatform = linux
   *   hypervisor = kvm
   *   guestOSPlatform = android
   *   guestMiddleware = androidSDV
   *   applicationMiddlewareAdapter = autoE2EToSCORE (derived by D-ASSET-APPLICATION-MIDDLEWARE-ADAPTER)
   *
   * Feature selections outside this projection (not resolved in SysML):
   *   sensingBoundary.perceptionSensors = camera
   *   capabilities.pedestrianDetection = disabled
   *   capabilities.bicycleDetection = disabled
   *   capabilities.adaptiveCruiseControl = disabled
   *   capabilities.laneKeepAssist = disabled
   *   capabilities.hmiDisplay = enabled
   */

  part :>> vehicleApplication = vehicleApplication::autoE2E;
  part :>> middleware = middleware::eclipseSCORE;
  part :>> osPlatform = osPlatform::linux;
  part :>> hypervisor = hypervisor::kvm;
  part :>> guestOSPlatform = guestOSPlatform::android;
  part :>> guestMiddleware = guestMiddleware::androidSDV;
  part :>> applicationMiddlewareAdapter = applicationMiddlewareAdapter::autoE2EToSCORE;
}
