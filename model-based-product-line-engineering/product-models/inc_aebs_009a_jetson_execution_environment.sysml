/*
 * Derived engineering execution-environment product-model projection — DO NOT EDIT.
 * Generated by configure_variant.py from a PLEML configuration receipt.
 * This is not a complete member-product specification.
 * Shared-assets source baseline: git-blob:998c47e198d51e8bcf0db46f90f48edffa5506cc:textual-notation-of-model/packages/architecture/execution_environments.sysml (content-addressed)
 * Shared-assets model: textual-notation-of-model/packages/architecture/execution_environments.sysml
 * Shared-assets model SHA-256: f35675c21dced2604c813b4a366b0cfbdd6a410ccb58539cb387188e89e538fc
 * Receipt: model-based-product-line-engineering/feature-models/receipts/engineering_execution_environments.receipt.json
 * Receipt SHA-256: 8ea9ac8d13addc4f540bb894a073480e3ed5652dd8be426db0f7b9091b68d278
 * Elements SHA-256: a187a596041311715bd7269e638d33da4275932512576bb5ee31ae5dad0259e5
 * Feature configuration: model-based-product-line-engineering/feature-configurations/inc_aebs_009a_jetson.sysml (incAEBS009AJetsonExecutionEnvironment)
 * Feature configuration SHA-256: 997c9625bd1974325a41a630e044eab20a13d8d2d53383de18250c0ebe77af61
 * PLEML feature model: model-based-product-line-engineering/feature-models/engineering_execution_environments.sysml
 * PLEML feature model SHA-256: 389d5cd4f7ae7e834b3a6705213d2b814255f17b5d8922b7e67244ae800ed1ef
 */

private import DE4SDV_ExecutionEnvironments::EngineeringExecutionEnvironment;

part def INCAEBS009AJetsonExecutionEnvironment :> EngineeringExecutionEnvironment {
  doc /*
   * Derived engineering execution-environment projection from PLEML configuration receipt.
   * Inspected exact System 2 environment currently maintained for INC-AEBS-009A: NVIDIA Jetson Orin Nano Developer Kit Super, Ubuntu 22.04 Tegra Linux, and native linux/arm64 OCI-container execution. Historical 009A runtime evidence proves a Jetson 8 GiB context but does not identify the exact SKU; this configuration therefore does not claim exact-SKU execution continuity.
   *
   * Variant selections:
   *   computeNode = jetsonOrinNano
   *   operatingSystem = ubuntu2204Tegra
   *   executionRuntime = nativeLinuxArm64OCI
   */

  part :>> computeNode = computeNode::jetsonOrinNano;
  part :>> operatingSystem = operatingSystem::ubuntu2204Tegra;
  part :>> executionRuntime = executionRuntime::nativeLinuxArm64OCI;
}
