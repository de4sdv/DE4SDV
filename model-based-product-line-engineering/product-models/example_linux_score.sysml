/*
 * Derived platform-stack product-model projection — DO NOT EDIT.
 * Generated by configure_variant.py from a PLEML configuration receipt.
 * This is not a complete member-product specification.
 * Shared-assets source baseline: git-blob:043a46f2ce8748c13ad5e30f87b91909f0a55fcb:textual-notation-of-model/packages/architecture/sdv_platform_stack.sysml (content-addressed)
 * Shared-assets model: textual-notation-of-model/packages/architecture/sdv_platform_stack.sysml
 * Shared-assets model SHA-256: 77c5cdd22035e028e1dd5cae0d7e5b69ec69eb1a6e14df4cf649ad70ce346b37
 * Receipt: model-based-product-line-engineering/feature-models/receipts/sdv_product_line.receipt.json
 * Receipt SHA-256: 76af6edd9457a9b3c1a76171c596a226200d7dba62738835a085fa8411ad448c
 * Elements SHA-256: f7c8b9439483aa66a2af75a52c31910b3c939042f5323500bb3b3ccc34c03dd4
 * Feature configuration: model-based-product-line-engineering/feature-configurations/example_linux_score_autoware.sysml (exampleLinuxSCOREVariant)
 * Feature configuration SHA-256: 6fe553ae70ef91a5ca3098a169a2f33e5b583dcb7bf9aa504b5576100fec1e57
 * PLEML feature model: model-based-product-line-engineering/feature-models/sdv_product_line.sysml
 * PLEML feature model SHA-256: 844409c296bb51ab539c39af9719274dc92b8c4219a04be12aee8596d94d6669
 */

private import DE4SDV_SDVPlatformStack::SDVPlatformStack;

part def ExampleLinuxSCOREVariant :> SDVPlatformStack {
  doc /*
   * Derived platform-stack projection from PLEML configuration receipt.
   * Single-domain reference configuration. Autoware (ADAS) on Eclipse S-CORE on Linux, no hypervisor. Vehicle-target AEBS only (no pedestrian/bicycle detection).
   *
   * Variant selections:
   *   vehicleApplication = autoware
   *   middleware = eclipseSCORE
   *   osPlatform = linux
   *   hypervisor = none
   *   applicationMiddlewareAdapter = autowareToSCORE (derived by D-ASSET-APPLICATION-MIDDLEWARE-ADAPTER)
   *
   * Feature selections outside this projection (not resolved in SysML):
   *   sensingBoundary.perceptionSensors = lidar, camera
   *   capabilities.pedestrianDetection = disabled
   *   capabilities.bicycleDetection = disabled
   *   capabilities.adaptiveCruiseControl = disabled
   *   capabilities.laneKeepAssist = disabled
   */

  part :>> vehicleApplication = vehicleApplication::autoware;
  part :>> middleware = middleware::eclipseSCORE;
  part :>> osPlatform = osPlatform::linux;
  part :>> hypervisor = hypervisor::none;
  part :>> applicationMiddlewareAdapter = applicationMiddlewareAdapter::autowareToSCORE;
}
