/*
 * Derived platform-stack product-model projection — DO NOT EDIT.
 * Generated by configure_variant.py.
 * This is not a complete member-product specification.
 * Shared-assets source baseline: git-blob:5271cb594699ddb3598cedd172ee5dda2e09156c:textual-notation-of-model/packages/architecture/sdv_platform_stack.sysml (content-addressed)
 * Shared-assets model: textual-notation-of-model/packages/architecture/sdv_platform_stack.sysml
 * Shared-assets model SHA-256: 70cbc35d95830a17c6128bb1dc99d570b6973c892488d82ed506d16347a8e342
 * Feature model SHA-256: 57b4f7eda267d4766adf7f1a96129d410ec7fce02bdb3c5df12a2d86ec7e591c
 * Bill-of-Features SHA-256: 8b608ae515d3a7401e6eb8c87ad7542946ae5194d3542c2a5bc9b8b649842380
 * Regenerate from: model-based-product-line-engineering/feature-configurations/mw-autoware-aaos-sdv-reference.yaml
 * Feature model: model-based-product-line-engineering/feature-models/sdv_product_line.yaml
 */

private import DE4SDV_SDVPlatformStack::SDVPlatformStack;

part def MWAutowareAAOSSDVReference :> SDVPlatformStack {
  doc /*
   * Derived platform-stack projection from Bill-of-Features.
   * Planned Autoware + AAOS SDV middleware reference member on the Android/KVM SDV Core platform domain with LiDAR and camera perception. Autoware retains its ROS 2/Linux application runtime; cross-domain deployment and transport remain unresolved. This configuration and its projection do not prove provider, generated binding, discovery, transport, adapter deployment, ROS 2 publication, Autoware observation, safety, compliance, or runtime interoperability.
   *
   * Variant selections:
   *   vehicleApplication = autoware
   *   middleware = androidSDV
   *   osPlatform = android
   *   hypervisor = kvm
   *   applicationMiddlewareAdapter = autowareToAAOSSDV (derived by D-ASSET-APPLICATION-MIDDLEWARE-ADAPTER)
   *
   * Feature selections outside this projection (not resolved in SysML):
   *   SensingBoundary.PerceptionSensors = LiDAR, Camera
   *   Capabilities.ForwardCollisionMitigation.PedestrianDetection = disabled
   *   Capabilities.ForwardCollisionMitigation.BicycleDetection = disabled
   *   Capabilities.AdaptiveCruiseControl = disabled
   *   Capabilities.LaneKeepAssist = disabled
   */

  part :>> vehicleApplication = vehicleApplication::autoware;
  part :>> middleware = middleware::androidSDV;
  part :>> osPlatform = osPlatform::android;
  part :>> hypervisor = hypervisor::kvm;
  part :>> applicationMiddlewareAdapter = applicationMiddlewareAdapter::autowareToAAOSSDV;
}
