/*
 * Derived platform-stack product-model projection — DO NOT EDIT.
 * Generated by configure_variant.py from a PLEML configuration receipt.
 * This is not a complete member-product specification.
 * Shared-assets source baseline: git-blob:59f17075eae082a430f9232efcfe203724154f76:textual-notation-of-model/packages/architecture/sdv_platform_stack.sysml (content-addressed)
 * Shared-assets model: textual-notation-of-model/packages/architecture/sdv_platform_stack.sysml
 * Shared-assets model SHA-256: 616dfce419346bf31cdfd9db1b54a3ecc99c577ad808d4e70dc22bdb96493557
 * Receipt: model-based-product-line-engineering/feature-models/receipts/sdv_product_line.receipt.json
 * Receipt SHA-256: b5fe031941baa6f43d7b8ab2c48b5d0bee992c2afe53d1cb4d1f21fc56bdcae1
 * Elements SHA-256: a187a596041311715bd7269e638d33da4275932512576bb5ee31ae5dad0259e5
 * Feature configuration: model-based-product-line-engineering/feature-configurations/apollo_qnx_qvm.sysml (apolloQNXQVMVariant)
 * Feature configuration SHA-256: 98d196d4b39b5bef9738048872779a3fa527f4b2dcec694e7ec9eb6f8f5f9169
 * PLEML feature model: model-based-product-line-engineering/feature-models/sdv_product_line.sysml
 * PLEML feature model SHA-256: a259b8a6736d81f204a7eaeb9f7a2bb13729a8658d1513f66eb40388dd91321f
 */

private import DE4SDV_SDVPlatformStack::SDVPlatformStack;

part def ApolloQNXQVMVariant :> SDVPlatformStack {
  doc /*
   * Derived platform-stack projection from PLEML configuration receipt.
   * Mixed-criticality reference configuration. Apollo (ADAS) on Eclipse S-CORE on QNX with QNX QVM hypervisor. Vehicle-target AEBS only.
   *
   * Variant selections:
   *   vehicleApplication = apollo
   *   middleware = eclipseSCORE
   *   osPlatform = qnx
   *   hypervisor = qvm
   *   guestOSPlatform = none
   *   guestMiddleware = none
   *   applicationMiddlewareAdapter = apolloToSCORE (derived by D-ASSET-APPLICATION-MIDDLEWARE-ADAPTER)
   *
   * Feature selections outside this projection (not resolved in SysML):
   *   sensingBoundary.perceptionSensors = lidar, radar
   *   capabilities.pedestrianDetection = disabled
   *   capabilities.bicycleDetection = disabled
   *   capabilities.adaptiveCruiseControl = disabled
   *   capabilities.laneKeepAssist = disabled
   *   capabilities.hmiDisplay = disabled
   */

  part :>> vehicleApplication = vehicleApplication::apollo;
  part :>> middleware = middleware::eclipseSCORE;
  part :>> osPlatform = osPlatform::qnx;
  part :>> hypervisor = hypervisor::qvm;
  part :>> guestOSPlatform = guestOSPlatform::none;
  part :>> guestMiddleware = guestMiddleware::none;
  part :>> applicationMiddlewareAdapter = applicationMiddlewareAdapter::apolloToSCORE;
}
